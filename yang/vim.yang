module vim
{
	namespace "http://cablelabs.com/yang/nfv/vim";
	prefix cablelabs;


  	import ietf-yang-types {
    		prefix yang;
    		revision-date 2010-09-24;
  	}
  	import ietf-inet-types {
    		prefix inet;
    		revision-date 2010-09-24;
  	}

  organization "CableLabs, Inc.";
  contact "Thomas Kee <t.kee@cablelabs.com>";

  description
    "This module contains a collection of YANG definitions for NFV.";

  	revision 2014-07-04 {
    		description
      		"Initial revision";
    		reference 
		"";
  	}

	typedef float {
		type binary {
			length "0..4";
		}
		description
		"32-bit IEEE floating point number" ;
	}
  


	grouping vm-resource-type
	{
		leaf id {
			type uint8 {
				range 0..255;
			}
			description
			"A unique numeric ID.";
		}
		leaf name {
			type string {
			     length "0..64";
			}
			description
			"A descriptive name, such as xx.size_name, is conventional but not required, though some third-party tools may rely on it.";
		}
		leaf memory {
			type uint64 {
				range 0..1000;
			}
			description
			"Virtual machine memory in megabytes.";
		}
		leaf disk {
			type uint8 {
				range 0..255;
			}
			description 
			"Virtual root disk size in gigabytes. ";
		}
		leaf ephemeral {
			type uint8 {
				range 0..255;
			}
			description
			"Specifies the size of a secondary ephemeral data disk. This is an empty, unformatted disk and exists only for the life of the instance.";
		}
		leaf vcpu {
			type uint8 {
				range 0..255;
			}
			description
			"Number of virtual CPUs presented to the instance.";
		}
		leaf rxtx {
			type float ;
			default 1.0;
			description
			"Optional property that allows created servers to have a different 
			bandwidth cap from that defined in the network they are attached to. 
			This factor is multiplied by the rxtx_base property of the network. 
			Default value is 1.0 (that is, the same as the attached network).";
		}
		leaf is-public {
			type boolean; 
			default true;
		}
	}

	
	typedef vm-state-type {
		type enumeration {
			enum "paused" {
				value 1;
			}
			enum "suspended" {
				value 2;
			}
			enum "active" {
				value 3;
			}
			enum "shutoff" {
				value 4;
			}
			enum "rescued" {
				value 5;
			}
			enum "stopped" {
				value 6;
			}
		}
	}

	typedef vm-action-type {
		type enumeration {
			enum "unpause" {
				value 1;
			}
			enum "resume" {
				value 2;
			}
			enum "rescue" {
				value 3;
			}
			enum "rebuild" {
				value 4;
			}
			enum "unrescue" {
				value 5;
			}
			enum "admin-password" {
				value 6;
			}
			enum "password" {
				value 7;
			}
			enum "stop" {
				value 8;
			}
		}
	}

	typedef vm-reference {
		type string;
		description
		"Type to identify the vm";
	}

	typedef tenant-reference {
		type string;
		description
		"Type to identify the tenant or project";
	}


	grouping vm-attributes-grouping {
				leaf vm-id
				{
					type vm-reference;
				}
		container vm-resources {
			uses vm-resource-type;
		}	
	        description "This grouping needed?";
	}


	grouping vm-list-grouping
	{
		container vm-managed {
			list vm-managed {
				key "vm-id";
				unique "vm-id";
				description
				"The list of all VMs ";
				uses vm-attributes-grouping;
			}
		}
	}



	rpc vim_vm_create {
			description
			"Create a vm";
			reference "";

			input {
				leaf tenant-id
				{
					type tenant-reference;
				}
				container vm-input
				{
					uses vm-attributes-grouping;
				}
			}
			output {
				leaf status
				{
					type uint32;
				}
				leaf vm-id
				{
					type vm-reference;
				}
			}
	}

	rpc vim_vm_get {
			description
			"Read a vm";
			reference "";

			input {
				leaf tenant-id
				{
					type tenant-reference;
				}
				leaf vm-id
				{
					type vm-reference;
				}
			}
			output {
				leaf status
				{
					type uint32;
				}
				leaf vm-state
				{
					type vm-state-type;
				}
				container vm-output
				{
					uses vm-attributes-grouping;
				}
			}
	}

	rpc vim_vm_update {
			description
			"Update a vm";
			reference "";

			input {
				leaf tenant-id
				{
					type tenant-reference;
				}
				leaf vm-id
				{
					type vm-reference;
				}
				container vm-output
				{
					uses vm-attributes-grouping;
				}
			}
			output {
				leaf status
				{
					type uint32;
				}
			}
	}

	rpc vim_vm_delete {
			description
			"delete a vm";
			reference "";

			input {
				leaf tenant-id
				{
					type tenant-reference;
				}
				leaf vm-id
				{
					type vm-reference;
				}
			}
			output {
				leaf status
				{
					type uint32;
				}
			}
	}

	rpc vim_vm_control {
			description
			"controller a vm";
			reference "";

			input {
				leaf tenant-id
				{
					type tenant-reference;
				}
				leaf vm-id
				{
					type vm-reference;
				}
				leaf vm-action {
					type vm-action-type;
				}
			}
			output {
				leaf status
				{
					type uint32;
				}
			}
	}

	rpc vim_vm_list {
			description
			"List all vms";
			reference "";

			input {
				leaf tenant-id
				{
					type tenant-reference;
				}
			}
			output {
				leaf status
				{
					type uint32;
				}
				container vm-list
				{
					uses vm-list-grouping;
				}
			}
	}
}
