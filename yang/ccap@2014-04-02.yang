module ccap {
    namespace "urn:cablelabs:params:xml:ns:yang:ccap";
    prefix ccap;
    import ietf-inet-types {
        prefix inet;
        revision-date 2010-09-24;
    }
    import ietf-yang-types {
        prefix yang;
        revision-date 2010-09-24;    }
    organization "Cable Television Laboratories, Inc.";
    contact 
        "Postal: Cable Television Laboratories, Inc.
         858 Coal Creek Circle
         Louisville, Colorado 80027-9750
         U.S.A.
         Phone: +1 303-661-9100
         Fax:   +1 303-661-9199
         E-mail: mibs@cablelabs.com";

    description "This module contains a collection of groupings and data definition statements related to CCAP system configuration and state.";
    reference "Data-Over-Cable Service Interface Specifications CCAP Operations Support System Interface Specification, CM-SP-CCAP-OSSI, Cable Television Laboratories, Inc.";
    revision 2014-04-02 {
        description "CCAP-OSSI I05 version.";
    }

    grouping host {
      choice address-or-hostname {
        mandatory true;
        case address {
          leaf address {
            mandatory true;
            type inet:ip-address;
          }
        }
        case name {
          leaf name {
            mandatory true;
            type inet:domain-name;
          }
        }
     }
     description
      "The host type represents either an strongly-typed IP address or a DNS
       domain name. Use of this type avoids the weak validation inherent in the 
       union-based inet:host type as with this type an ip-address cannot be 
       inappropriately validated as a domain-name accidentally.";
   }

    typedef ccap-octet-data-type {
        type string {
            pattern "([0-9a-fA-F]{2})*";
        }
        description "A derived type representing the lexical value space of XML Schema hexBinary defined as 'each binary octet is encoded as a character tuple, consisting of two hexadecimal digits ([0-9a-fA-F]) representing the octet code.' Please note that length constraints on this derived type needs to be in multiples of 2 to avoid conflicts between length and pattern space";
        reference "[XML-Schema] 3.2.15 hexBinary";
    }

  typedef ip-host-prefix {
    type union {
      type ipv4-host-prefix;
      type ipv6-host-prefix;
    }
    description
     "The ip-prefix type represents an IP host address plus prefix and is IP
      version neutral.  The format of the textual representations
      implies the IP version. This type is similar to inet:ip-prefix.";
  }

  typedef ipv4-host-prefix {
    type string {
      pattern
         '(([0-9]|[1-9][0-9]|1[0-9][0-9]|2[0-4][0-9]|25[0-5])\.){3}'
       +  '([0-9]|[1-9][0-9]|1[0-9][0-9]|2[0-4][0-9]|25[0-5])'
       + '/(([0-9])|([1-2][0-9])|(3[0-2]))';
    }
    description
     "The ipv4-host-prefix type represents an IPv4 host address
      plus the prefix length, separated by a slash.
      The prefix length is given by the number following the
      slash character and must be less than or equal to 32.

      A prefix length value of n corresponds to an IP address
      mask that has n contiguous 1-bits from the most
      significant bit (MSB) and all other bits set to 0.

      This type is derived from the inet:ipv4-prefix type,
      which has all bits of the IPv4 address set to zero that
      are not part of the IPv4 prefix. Use of that type requires 
      separate configuration of the interface host address.";
  }

  typedef ipv6-host-prefix {
    type string {
      pattern '((:|[0-9a-fA-F]{0,4}):)([0-9a-fA-F]{0,4}:){0,5}'
            + '((([0-9a-fA-F]{0,4}:)?(:|[0-9a-fA-F]{0,4}))|'
            + '(((25[0-5]|2[0-4][0-9]|[01]?[0-9]?[0-9])\.){3}'
            + '(25[0-5]|2[0-4][0-9]|[01]?[0-9]?[0-9])))'
            + '(/(([0-9])|([0-9]{2})|(1[0-1][0-9])|(12[0-8])))';
      pattern '(([^:]+:){6}(([^:]+:[^:]+)|(.*\..*)))|'
            + '((([^:]+:)*[^:]+)?::(([^:]+:)*[^:]+)?)'
            + '(/.+)';
    }
    description
     "The ipv6-host-prefix type represents an IPv4 host address
      plus the prefix length, separated by a slash.
      The prefix length is given by the number following the
      slash character and must be less than or equal to 128.

      A prefix length value of n corresponds to an IP address
      mask that has n contiguous 1-bits from the most
      significant bit (MSB) and all other bits set to 0.

      This type is derived from the inet:ipv6-prefix type,
      which has all bits of the IPv6 address set to zero that
      are not part of the IPv6 prefix. Use of that type requires 
      separate configuration of the interface host address.

      The IPv6 address is represented
      in the compressed format described in RFC 4291, Section
      2.2, item 2 with the following additional rules: the ::
      substitution must be applied to the longest sequence of
      all-zero 16-bit chunks in an IPv6 address.  If there is
      a tie, the first sequence of all-zero 16-bit chunks is
      replaced by ::.  Single all-zero 16-bit chunks are not
      compressed.  The canonical format uses lowercase
      characters and leading zeros are not allowed.";
    reference
     "RFC 4291: IP Version 6 Addressing Architecture";
  }
    typedef primary-ds-indicator-type {
        type enumeration {
            enum other {
                value 1;
            }
            enum primary-ds-channel {
                value 2;
            }
            enum backup-primary-channel {
                value 3;
            }
            enum not-specified {
                value 4;
            }
        }
    }
    typedef acl-comparator-type {
        type enumeration {
            enum other {
                value 0;
            }
            enum lt {
                value 1;
            }
            enum gt {
                value 2;
            }
            enum eq {
                value 3;
            }
            enum neq {
                value 4;
            }
        }
    }
    typedef load-bal-init-tech-type {
      type bits {
          bit reinit-mac {
              position 0;
          }
          bit broadcast-ranging {
              position 1;
          }
          bit unicast-ranging {
              position 2;
          }
          bit ranging {
              position 3;
          }
          bit direct {
              position 4;
          }
          bit disable {
              position 5;
          }
     }
      description "Initialization techniques used when changing channels in load balancing groups.
                  An empty value means no channel changes allowed.";
    }
    typedef load-balancing-rule-type {
        type enumeration {
            enum other {
                value 1;
                description "The value of other is used when a vendor-extension has been implemented for this attribute.";
            }
            enum enabled {
                value 2;
            }
            enum disabled {
                value 3;
            }
            enum disabled-period {
                value 4;
            }
        }
    }
    typedef interleaver-depth-type {
        type enumeration {
            enum other {
                value 1;
                description "The value of other is used when a vendor-extension has been implemented for this attribute.";
            }
            enum fecI8J16 {
                value 2;
            }
            enum fecI12J17 {
                value 3;
            }
            enum fecI16J8 {
                value 4;
            }
            enum fecI32J4 {
                value 5;
            }
            enum fecI64J2 {
                value 6;
            }
            enum fecI128J1 {
                value 7;
            }
            enum fecI128J2 {
                value 8;
            }
            enum fecI128J3 {
                value 9;
            }
            enum fecI128J4 {
                value 10;
            }
            enum fecI128J5 {
                value 11;
            }
            enum fecI128J6 {
                value 12;
            }
            enum fecI128J7 {
                value 13;
            }
            enum fecI128J8 {
                value 14;
            }
        }
    }
    typedef qam-modulation-type {
        type enumeration {
            enum other {
                value 1;
                description "The value of other is used when a vendor-extension has been implemented for this attribute.";
            }
            enum qam64 {
                value 2;
            }
            enum qam128 {
                value 3;
            }
            enum qam256 {
                value 4;
            }
            enum qam512 {
                value 5;
            }
            enum qam1024 {
                value 6;
            }
        }
        description "This value defines the type of Downstream QAM Modulation.";
    }
    typedef ca-encryptor-type-type {
        type enumeration {
            enum other;
            enum motorola;
            enum cisco;
            enum simulcrypt;
        }
    }
    typedef encryption-scheme-type {
        type enumeration {
            enum other {
                value 1;
                description "The value of other is used when a vendor-extension has been implemented for this attribute.";
            }
            enum des {
                value 2;
            }
            enum aes {
                value 3;
            }
            enum 3des {
                value 4;
            }
            enum dvbcsa {
                value 5;
            }
            enum dvbcsa3 {
                value 6;
            }
        }
    }
    typedef encryption-algorithm-ctl-type {
        type enumeration {
	    enum other {
	        value 1;
		description "The value of other is used when a vendor-extension has been implemented for this attribute.";
	    }
	    enum cmts {
	        value 2;
	    }
	    enum mgmt {
	        value 3;
	    }
	}
	description "This enumerates the set of ways a CMTS can select the encryption algorithm. Whether the CMTS can select the algorithm or if this can be set manually using the Alg attribute. If this attribute is set to 'cmts', the CMTS can select the encryption algorithm for the Security Association (SA). If this attribute is set to 'mgmt', the Alg attribute is used to define the encryption algorithm for this SA.";
    }
    typedef encryption-algorithm-type {
        type enumeration {
	    enum other {
	        value 1;
		description "The value of other is used when a vendor-extension has been implemented for this attribute.";
	    }
	    enum des56-cbc-mode {
	        value 2;
	    }
	    enum des40-cbc-mode {
	        value 3;
	    }
	    enum aes128-cbc-mode {
	        value 4;
	    }
	}
	description "This enumerates the set of possible encryption algorithms which can be used for a Security Association";
    }
    typedef cert-revocation-method-type {
      type enumeration {
	  enum other {
	      value 1;
	      description "The value of other is used when a vendor-extension has been implemented for this attribute.";
	  }
	  enum none {
	      value 2;
	  }
	  enum crl {
	      value 3;
	  }
	  enum ocsp {
	      value 4;
	  }
	  enum crl-and-ocsp {
	      value 5;
	  }
      }
      description 
	"This enumerates the set of certificate revocation methods which can used by the CMTS to verify the cable modem certificate validity. The certificate revocation methods include Certification Revocation List (CRL) and Online Certificate Status Protocol (OCSP).
         The following options are available:
             The option 'none' indicates that the CMTS does not attempt to determine the revocation status of a certificate.
             The option 'crl' indicates the CMTS uses a Certificate Revocation List (CRL) as defined by the Url attribute of the CmtsCertRevocationList object. When the value of this attribute is changed to 'crl', it triggers the CMTS to retrieve the CRL file from the URL specified by the Url attribute. If the value of this attribute is 'crl' when the CMTS starts up, it triggers the CMTS to retrieve the CRL file from the URL specified by the Url attribute.
             The option 'ocsp' indicates the CMTS uses the Online Certificate Status Protocol (OCSP) as defined by the Url attribute of the CmtsOnlineCertStatusProtocol object.
             The option 'crlAndOcsp' indicates the CMTS uses both the CRL as defined by the Url attribute in the CmtsCertRevocationList object and OCSP as defined by the Url attribute in the CmtsOnlineCertStatusProtocol object.";
    }
    typedef filter-action-type {
        type enumeration {
	    enum other {
	        value 1;
		description "The value of other is used when a vendor-extension has been implemented for this attribute.";
	    }
	    enum permit {
	        value 2;
	    }
	    enum deny {
	        value 3;
	    }
	}
	description "This enumerates the set of actions which can be taken upon this filter matching. 'permit' means to stop the classification matching and accept the packet for further processing. 'deny' means to drop the packet.";
    }
    typedef upstream-fec-mode-type {
        type enumeration {
            enum other;
            enum enabled;
            enum disabled;
            enum perOnu;
        }
        reference 
            "CCAP Operations Support System Interface Specification
             CM-SP-CCAP-OSSI-I01-110930 UpstreamFecMode section.";
    }
    typedef downstream-fec-mode-type {
        type enumeration {
            enum other;
            enum enabled;
            enum disabled;
            enum perOnu;
        }
        reference 
            "CCAP Operations Support System Interface Specification
             CM-SP-CCAP-OSSI-I01-110930 DownstreamFecMode section.";
    }
    typedef downstream-allocation-type {
        type enumeration {
	    enum other {
	        value 1;
		  description "The value of other is used when a vendor-extension has been implemented for this attribute.";
	    }
	    enum docsis-only {
	        value 2;
	    }
	    enum video-only {
	        value 3;
	    }
	    enum any {
	        value 4;
	    }
	}
	description "This enumerates the services a DownChannel instance can be allocated to. A value of 'any' means that the ERM could configure the QAM resource for either video or DOCSIS. The value of other(1) is used when a vendor-extension has been implemented for this attribute.";
	}
    typedef cipher-type {
        type bits {
            bit other {
                position 0;
            }
            bit des3 {
                position 1;
                description "Really 3des, but that is not allowed in YANG.";
            }
            bit aes128 {
                position 2;
            }
            bit aes192 {
                position 3;
            }
            bit aes256 {
                position 4;
            }
            bit arcfour {
                position 5;
            }
            bit blowfish {
                position 6;
            }
            bit cast {
                position 7;
            }
            bit twofish128 {
                position 8;
            }
            bit twofish192 {
                position 9;
            }
            bit twofish256 {
                position 10;
            }
        }
        description "Set of encryption algorithms uses, e.g., for ssh.";
    }
    typedef auth-code-type {
        type bits {
            bit other {
                position 0;
            }
            bit md5 {
                position 1;
            }
            bit md5-96 {
                position 2;
            }
            bit sha1 {
                position 3;
            }
            bit sha1-96 {
                position 4;
            }
            bit ripemd-160 {
                position 5;
            }
            bit sha2-256 {
                position 6;
            }
            bit sha2-512 {
                position 7;
            }
        }
        description "Set of message authentication algorithms used, e.g., for ssh.";
    }
    typedef host-auth-type {
        type enumeration {
            enum other {
                value 0;
            }
            enum none {
                value 1;
            }
            enum ssh-dss {
                value 2;
            }
            enum ssh-rsa {
                value 3;
            }
            enum pgp-sign-rsa {
                value 4;
            }
            enum pgp-sign-dss {
                value 5;

            }
        }
        description "Public key format used, e.g., in ssh host authentication.";
    }
    typedef trigger-flag-type {
        type bits {
            bit registration {
                position 0;
            }
            bit ranging-retry {
                position 1;
            }
        }
        description "This data type defines the union of Diagnostic Log trigger types. Bit 0 represents the registration trigger, Bit 1 represents the ranging retry trigger.";
        reference 
            "DOCSIS 3.0 Operations Support System Interface Specification
             CM-SP-OSSIv3.0-I15-110623 Diagnostic Log Annex.";
    }
    typedef admin-state-type {
        type enumeration {
            enum other {
                value 1;
                description "The value of other is used when a vendor-extension has been implemented for this attribute.";
            }
            enum up {
                value 2;
            }
            enum down {
                value 3;
            }
            enum testing {
                value 4;
            }
        }
        description "This data type defines the admin state. The value of 'other' is used when a vendor extension has been implemented for this attribute.";
        reference "RFC 2863";
    }
    typedef attribute-mask-type {
        type bits {
            bit bonded {
                position 0;
            }
            bit low-latency {
                position 1;
            }
            bit high-availability {
                position 2;
            }
            bit reserved-3 {
                position 3;
            }
            bit reserved-4 {
                position 4;
            }
            bit reserved-5 {
                position 5;
            }
            bit reserved-6 {
                position 6;
            }
            bit reserved-7 {
                position 7;
            }
            bit reserved-8 {
                position 8;
            }
            bit reserved-9 {
                position 9;
            }
            bit reserved-10 {
                position 10;
            }
            bit reserved-11 {
                position 11;
            }
            bit reserved-12 {
                position 12;
            }
            bit reserved-13 {
                position 13;
            }
            bit reserved-14 {
                position 14;
            }
            bit reserved-15 {
                position 15;
            }
            bit operator-16 {
                position 16;
            }
            bit operator-17 {
                position 17;
            }
            bit operator-18 {
                position 18;
            }
            bit operator-19 {
                position 19;
            }
            bit operator-20 {
                position 20;
            }
            bit operator-21 {
                position 21;
            }
            bit operator-22 {
                position 22;
            }
            bit operator-23 {
                position 23;
            }
            bit operator-24 {
                position 24;
            }
            bit operator-25 {
                position 25;
            }
            bit operator-26 {
                position 26;
            }
            bit operator-27 {
                position 27;
            }
            bit operator-28 {
                position 28;
            }
            bit operator-29 {
                position 29;
            }
            bit operator-30 {
                position 30;
            }
            bit operator-31 {
                position 31;
            }
        }
    }
    typedef downstream-phy-type {
        type enumeration {
            enum other {
                value 1;
                description "The value of other is used when a vendor-extension has been implemented for this attribute.";
            }
            enum dvbc {
                value 2;
            }
            enum j83annexB {
                value 3;
            }
            enum j83annexC {
                value 4;
            }
        }
    }
    typedef msc-state-type {
        type enumeration {
            enum other {
                value 1;
                description "The value of other is used when a vendor-extension has been implemented for this attribute.";
            }
            enum channel-enabled {
                value 2;
            }
            enum channel-disabled {
                value 3;
            }
            enum dormant {
                value 4;
            }
        }
    }
    typedef us-channel-type {
        type enumeration {
            enum other {
                value 1;
                description "The value of other is used when a vendor-extension has been implemented for this attribute.";
            }
            enum tdma {
                value 2;
            }
            enum atdma {
                value 3;
            }
            enum scdma {
                value 4;
            }
            enum tdmaAndAtdma {
                value 5;
            }
        }
        description "Indicates the DOCSIS Upstream Channel Type. ";
    }
    typedef us-channel-width {
        type enumeration {
	    enum other;
	    enum 200000;
	    enum 400000;
	    enum 800000;
	    enum 1600000;
	    enum 3200000;
	    enum 6400000;
        }
	description "The upstream channel width in Hertz.";
    }
    typedef direction-type {
        type enumeration {
	    enum other {
	        value 1;
		description "The value of other is used when a vendor-extension has been implemented for this attribute.";
	    }
	    enum downstream {
	        value 2;
	    }
	    enum upstream {
	        value 3;
	    }
	}
	description "This enumerates the set of potential Direction values for the QoS Parameter Set.";
    }
    typedef ds-resequencing-type {
        type enumeration {
	    enum other {
	        value 1;
		description "The value of other is used when a vendor-extension has been implemented for this attribute.";
	    }
	    enum resequencing-dsid {
	        value 2;
	    }
	    enum no-resequencing-dsid {
	        value 3;
	    }
	}
	description "This enumerates the set of potential DsResequencing values for the QoS Parameter Set.";
    }
    typedef service-flow-scheduling-type {
        type enumeration {
	    enum other {
	        value 1;
		description "The value of other is used when a vendor-extension has been implemented for this attribute.";
	    }
	    enum best-effort {
	        value 2;
	    }
	    enum non-real-time-polling-service {
	        value 3;
	    }
	    enum real-time-polling-service {
	        value 4;
	    }
	    enum unsolicited-grant-service-with-ad {
	        value 5;
	    }
	    enum unsolicited-grant-service {
	        value 6;
	    }
	}
	description "This enumerates the set of possible SchedulingType values for the QoS Parameter Set.";
    }
    typedef ip-prov-mode-type {
        type enumeration {
            enum other {
                value 1;
                description "The value of other is used when a vendor-extension has been implemented for this attribute.";
            }
            enum ipv4-only {
                value 2;
            }
            enum ipv6-only {
                value 3;
            }
            enum alternate {
                value 4;
            }
            enum dual-stack {
                value 5;
            }
        }
        default ipv6-only;
    }
    typedef duplex-type {
        type enumeration {
	    enum other {
	        value 1;
		description "The value of other is used when a vendor-extension has been implemented for this attribute.";
	    }
	    enum full-duplex {
	        value 2;
	    }
	    enum half-duplex {
	        value 3;
	    }
	    enum auto-negotiation {
	        value 4;
	    }
	}
	description "This enumerates the Ethernet DuplexStates of an interface can be in. The value of other(1) is used when a vendor-extension has been implemented for this attribute.";
    }
    typedef ethernet-speed-type {
        type enumeration {
	    enum other {
	        value 1;
		description "The value of other is used when a vendor-extension has been implemented for this attribute.";
	    }
	    enum ten-mb-ethernet {
	        value 2;
	    }
	    enum hundred-mb-ethernet {
	        value 3;
	    }
	    enum one-gb-ethernet {
	        value 4;
	    }
	    enum auto {
	        value 5;
	    }
	}
	description "This enumerates the set of possible ethernet interface speeds. The value of other(1) is used when a vendor-extension has been implemented for this attribute.";
    }
    typedef ethernet-protocol-id-type {
        type enumeration {
	    enum other {
	        value 1;
		description "The value of other is used when a vendor-extension has been implemented for this attribute.";
	    }
	    enum none {
	        value 2;
	    }
	    enum ethertype {
	        value 3;
	    }
	    enum dsap {
	        value 4;
	    }
	    enum mac {
	        value 5;
	    }
	    enum all {
	        value 6;
	    }
	}
	description 
	    "This enumerates the set of formats of the layer 3 protocol ID in the Ethernet frame. A value of 'none' means that the rule does not use the layer 3 protocol type as a matching criteria. A value of 'ethertype' means that the rule applies only to frames that contain an EtherType value. Ethertype values are contained in packets using the DEC-Intel- Xerox (DIX) encapsulation or the [RFC 1042] Sub-Network Access Protocol (SNAP) encapsulation formats. A value of 'dsap' means that the rule applies only to frames using the IEEE802.3 encapsulation format with a Destination Service Access Point (DSAP) other than 0xAA (which is reserved for SNAP). A value of 'mac' means that the rule applies only to MAC management messages for MAC management messages. A value of 'all' means that the rule matches all Ethernet frame. If the Ethernet frame contains an 802.1P/Q Tag header (i.e., EtherType 0x8100), this attribute applies to the embedded EtherType field within the 802.1p/Q header.
             The value 'mac' is only used for passing UDCs to CMs during Registration. The CMTS ignores filter rules that include the value of this attribute set to 'mac' for CMTS enforced upstream and downstream subscriber management filter group rules.";
	reference "RFC 1042 Sub-Network Access Protocol (SNAP) encapsulation formats.";
    }
    typedef pon-symmetry-type {
        type enumeration {
	    enum other {
	        value 1;
		description "The value of other is used when a vendor-extension has been implemented for this attribute.";
	    }
	    enum symmetric-10x10 {
	        value 2;
	    }
	    enum asymmetric-10x1 {
	        value 3;
	    }
	}
	description "This enumerates the set of possible PON interface speeds allowing for asymmetrical upstream and downstream speeds. The value of other(1) is used when a vendor-extension has been implemented for this attribute.";
    }
    typedef qos-control-type {
        type enumeration {
            enum other {
                value 1;
                description "The value of other is used when a vendor-extension has been implemented for this attribute.";
            }
            enum single-session {
                value 2;
            }
            enum aggregate-session {
                value 3;
            }
        }
        description "This attribute identifies how Group Classifier Rules (GCRs) and Group Service Flows (GSFs) are instantiated when multiple sessions match the (S,G) criteria of this entry. If 'singleSession', the CMTS creates a unique GCR and a unique GSF for the session. If this object's value is 'aggregateSession', all sessions matching this criterion are aggregated into the same GSF.";
    }
    typedef upstream-frequency-range-type {
        type enumeration {
            enum other {
                value 1;
                    description "The value of other is used when a vendor-extension has been implemented for this attribute.";
            }
            enum standard {
                value 2;
            }
            enum extended {
                value 3;
            }
        }
        description "This attribute indicates in MDD messages the upstream frequency upper band edge of an upstream Channel. A value 'standard' means Standard Frequency Range and a value 'extended' means Extended Frequency Range.";
        reference "DOCSIS 3.0 Operations Support System Interface Specification CM-SP-OSSIv3.0-I15-110623 MdCfg Object section.";
    }
    typedef early-auth-encrypt-control-type {
        type enumeration {
            enum other {
                value 1;
                description "The value of other is used when a vendor-extension has been implemented for this attribute.";
            }
            enum disable-eae {
                value 2;
            } 
            enum enable-eae-ranging-based-enforcement {
                value 3;
            }
            enum enable-eae-capability-based-enforcement {
                value 4;
            }
            enum enable-eae-total-enforcement {
                value 5;
            }
        }
        description "This attribute enables or disables early authentication and encryption (EAE) signaling for the MAC Domain. It also defines the type of EAE enforcement in the case that EAE is enabled. If set to 'disable-eae', EAE is disabled for the MAC Domain. If set to 'enable-eae-ranging-based-enforcement', 'enable-eae-capability-based-enforcement' or 'enable-eae-total-enforcement', EAE is enabled for the MAC Domain. The following EAE enforcement methods are defined in the case where EAE signaling is enabled: - The option 'enable-eae-ranging-based-enforcement' indicates EAE is enforced on CMs that perform ranging with a B-INIT-RNG-REQ message. - The option 'enable-eae-capability-based-enforcement' indicates EAE is enforced on CMs that perform ranging with a B-INIT-RNG-REQ message in which the EAE capability flag is set. The option 'enable-eae-total-enforcement' indicates EAE is enforced on all CMs regardless of their EAE capabilities.";
        reference "DOCSIS 3.0 Operations Support System Interface SpecificationCM-SP-OSSIv3.0-I15-110623 MdCfg Object section.";
    }
    typedef bpi2-enforce-control-type {
        type enumeration {
            enum other {
                value 1;
                description "The value of other is used when a vendor-extension has been implemented for this attribute.";
            }
            enum disable {
                value 2;
            }
            enum qosCfgFileWithBpi2AndCapabPrivSupportEnabled {
                value 3;
            }
            enum qosCfgFileWithBpi2Enabled {
                value 4;
            }
            enum qosCfgFile {
                value 5;
            }
            enum total {
                value 6;
            }
        }
        description "This attribute indicates the level of BPI+ enforcement policies with the MAC Domain.";
        reference "DOCSIS 3.0 Operations Support System Interface SpecificationCM-SP-OSSIv3.0-I15-110623 MdCfg Object section.";
    }
    typedef enable-type {
        type enumeration {
            enum other {
                value 1;
                description "The value of other is used when a vendor-extension has been implemented for this attribute.";
            }
            enum enable {
                value 2;
            }
            enum disable {
                value 3;
            }
        }
       description "This attribute enables the enforcement of Multicast Authorization feature. When this attribute is set to 'enable', Multicast Authorization is enforced; otherwise, clients are permitted to join any IP multicast session. The factory default value of this attribute is 'disable'.";
    }
    typedef authorization-action-type {
        type enumeration {
            enum other {
                value 1;
                description "The value of other is used when a vendor-extension has been implemented for this attribute.";
            }
            enum accept {
                value 2;
            }
            enum deny {
                value 3;
            }
        }
        description "This attribute specifies the authorization action for a session join attempt. The value 'accept' indicates that a multicast join request is allowed. The value 'deny' indicates that a multicast join request is denied.This type is used for both default behavior (i.e. a session 'join' request matches no session rules) and explicitly configured behavior (i.e. a session 'join' request matches the session rule)";        
    }
    typedef modulation-interval-usage-code-type {
        type enumeration {
            enum request {
                value 1;
            }
            enum requestData {
                value 2;
            }
            enum initialRanging {
                value 3;
            }
            enum periodicRanging {
                value 4;
            }
            enum shortData {
                value 5;
            }
            enum longData {
                value 6;
            }
            enum advPhyShortData {
                value 9;
            }
            enum advPhyLongData {
                value 10;
            }
            enum ugs {
                value 11;
            }
        }
        description "An index into the Channel Modulation table that, when grouped with other Interval Usage Codes, fully instantiates all modulation sets for a given upstream channel.";
    }
    typedef modulation-type {
        type enumeration {
            enum other {
                value 1;
                description "The value of other is used when a vendor-extension has been implemented for this attribute.";
            }
            enum qpsk {
                value 2;
            }
            enum qam8 {
                value 3;
            }
            enum qam16 {
                value 4;
            }
            enum qam32 {
                value 5;
            }
            enum qam64 {
                value 6;
            }
            enum qam128 {
                value 7;
            }
        }
        description "The modulation type in transmissions using this IUC.";
    }
    typedef preamble-length-type {
        type uint16 {
            range "0..1536";
        }
        units bits;
        description "The preamble length for this modulation profile in bits.";
    }
    typedef fec-error-correction-type {
        type uint8 {
            range "0..16";
        }
        units Bytes;
        description "The number of correctable errored bytes (t) used in forward error correction code.  The value of 0 indicates that no correction is employed.  The number of check bytes appended will be twice this value.";
    }
    typedef fec-codeword-length-type {
        type uint8 {
            range "1..255";
        }
        units Bytes;
        description "The number of correctable errored bytes (t) used in forward error correction code.";
    }
    typedef scrambler-seed-type {
        type uint16 {
            range "0..32767";
        }
        description "The 15-bit seed value for the scrambler polynomial.";
    }
    typedef preamble-type {
       type enumeration {
           enum other {
               value 1;
               description "The value of other is used when a vendor-extension has been implemented for this attribute.";
           }
           enum qpsk0 {
               value 2;
           }
           enum qpsk1 {
               value 3;
           }
       }
       description "Preamble type for DOCSIS 2.0 bursts.  ";
    }
    typedef scdma-interleaver-step-size-type {
        type uint8 {
            range "0 | 1..32";
        }
        description "S-CDMA Interleaver step size.";
    }
    typedef scdma-subframe-codes-type {
        type uint8 {
            range "0 | 1..128";
        }
        description "S-CDMA sub-frame size.";
    }
    typedef dsg-client-id-class-type {
        type enumeration {
            enum other {
                value 1;
                description "The value of other is used when a vendor-extension has been implemented for this attribute.";
            }
            enum broadcast {
                value 2;
            }
            enum mac-address {
                value 3;
            }
            enum ca-system-id {
                value 4;
            }
            enum application-id {
                value 5;
            }
        }
        description "The DSG Client Identification type. A DSG client id of type broadcast(1) received by all DSG client(s). A DSG client id of type macAddress(2) is received by the DSG client that has been assigned with this MAC address where the first 3 bytes is the Organization Unique Identifier (OUI). A DSG client id of type caSystemId(3) is received by the DSG client that has been assigned a CA_system_ID. A DSG client ID of type applicationId(4) is received by the DSG client that has been assigned an application ID. The value of other(1) is used when a vendor-extension has been implemented for this attribute.";
    }
    typedef non-zero-seconds-type {
        type uint8 {
            range "1..60";
        }
        units seconds;
        description "The non-zero seconds in a minute.";
    }
    typedef ack-sequence-interval-type {
        type uint16 {
            range "1..500";
        }
        units records;
        description "The maximum number of unacknowledged records that can be sent by the CCAP IPDR exporter before receiving an acknowledgement.";
    }
    typedef seconds-day-max-type {
        type uint32 {
            range "0..86400";
        }
        units seconds;
        description "The number of seconds between 0 and 1 day.";
    }
    typedef ipdr-streaming-type {
        type enumeration {
            enum other {
                value 1;
                description "The value of other is used when a vendor-extension has been implemented for this attribute.";
            }
            enum time-interval {
                value 2;
            }
            enum ad-hoc {
                value 3;
            }
            enum event {
                value 4;
            }
            enum time-event {
                value 5;
            }
        }
        description "This attribute configures the type of IPDR streaming used for the session. See the IPDR Service Definition Schemas section of [OSSIv3.0] for the streaming types supported by each Service Definition. The value of other(1) is used when a vendor-extension has been implemented for this attribute.";
    }
    typedef ipdr-service-definition-type {
        type enumeration {
            enum other {
                value 1;
                description "The value of other is used when a vendor-extension has been implemented for this attribute.";
            }
            enum cmts-cm-service-flow-type {
                value 2;
            }
            enum cmts-cm-reg-status-type {
                value 3;
            }
            enum cmts-cm-us-stats-type {
                value 4;
            }
            enum cmts-ds-util-stats-type {
                value 5;
            }
            enum cmts-us-util-stats-type {
                value 6;
            }
            enum cmts-topology-type {
                value 7;
            }
            enum cpe-type {
                value 8;
            }
            enum diag-log-type {
                value 9;
            }
            enum diag-log-detail-type {
                value 10;
            }
            enum diag-log-event-type {
                value 11;
            }
            enum samis-type-1 {
                value 12;
            }
            enum samis-type-2 {
                value 13;
            }
            enum spectrum-measurement-type {
                value 14;
            }
        }
        description "This attribute configures the service type definition for this IPDR session. See the IPDR Service Definition Schemas section of [OSSIv3.0] for the definitions and schemas of the types defined in this enumeration. The value of other(1) is used when a vendor-extension has been implemented for this attribute.";
    }
    typedef table-interval-type {
        type uint8 {
            range "0..32";
        }
        units "tables per second";
        description "A table interval expressed in tables/second.";
    }
    typedef video-pid-usage-type {
        type enumeration {
            enum other {
                value 1;
                description "The value of other is used when a vendor-extension has been implemented for this attribute.";
            }
            enum emm {
                value 2;
            }
            enum nit {
                value 3;
            }
            enum cat {
                value 4;
            }
            enum pat {
                value 5;
            }
            enum fixed {
                value 6;
            }
            enum eas {
                value 7;
            }
            enum dsm-cc {
                value 8;
            }
            enum eiss {
                value 9;
            }
            enum etvbif {
                value 10;
            }
            enum video {
                value 11;
            }
            enum audio {
                value 12;
            }
        }
        description "This enumeration defines the type of the identified PID stream. This value is used to understand what anchor table (i.e., PAT, CAT) would need to be updated, in case PidRemapEnable is set to True and a remap is required. In case of type 'eas', the table sections of the PID stream may need to be interleaved with other table sections that would be present on the same OutputPid. 'dsm-cc' is used for digital storage media command and control. 'eiss' is used for ETV Integrated Signaling Streams (Stream type 0xC0 or 0x05 w-descriptor tag 0xA2). 'etvbif' is used for ETV Binary Interchange Format (Stream type 0xC0 or 0x05 w-descriptor tag 0xA1 OR Stream Type 0X0B). 'video' is used for MPEG2 video streams. 'audio' is used for MPEG2 audio streams. The value of other(1) is used when a vendor-extension has been implemented for this attribute.";
    }
    typedef cci-level-type {
        type enumeration {
            enum other {
                value 1;
                description "The value of other is used when a vendor-extension has been implemented for this attribute.";
            }
            enum copy-freely {
                value 2;
            }
            enum copy-one-generation {
                value 3;
            }
            enum copy-no-more {
                value 4;
            }
            enum copy-never {
                value 5;
            }
        }
        description "This attribute represents the Copy Control Indicator/Digital Rights protection applicable to the program. It is forwarded to all active ECMGs to be encapsulated into ECMs. The value of other(1) is used when a vendor-extension has been implemented for this attribute.";
    }
    typedef cit-type {
        type enumeration {
            enum other {
                value 1;
                description "The value of other is used when a vendor-extension has been implemented for this attribute.";
            }
            enum clear {
                value 2;
            }
            enum set {
                value 3;
            }
        }
        description "This attribute represents the Constrained Image Trigger flag applicable to the program. It is forwarded to all active ECMGs to be encapsulated into ECMs. The value of other(1) is used when a vendor-extension has been implemented for this attribute.";
    }
    typedef rct-type {
        type enumeration {
            enum other {
                value 1;
                description "The value of other is used when a vendor-extension has been implemented for this attribute.";
            }
            enum not-asserted {
                value 2;
            }
            enum required {
                value 3;
            }
        }
        description "This attribute represents the Redistribution Control Trigger flag applicable to the program. It is forwarded to all active ECMGs to be encapsulated into ECMs. The value of other(1) is used when a vendor-extension has been implemented for this attribute.";

    }
    typedef cci-reserved-type {
        type uint8 {
            range "0..3";
        }
        description "This attribute reserves 2 bits of copy control information (CCI) for future use. It is forwarded to all active ECMGs to be encapsulated into ECMs.";
    }
    typedef key-length-type {
        type enumeration {
            enum other {
                value 1;
                description "The value of other is used when a vendor-extension has been implemented for this attribute.";
            }
            enum 56bits {
                value 2;
            }
            enum 128bits {
                value 3;
            }
            enum 192bits {
                value 4;
            }
            enum 256bits {
                value 5;
            }
        }
        description "This attribute configures the number of bits in the encryption keys used by encryption algorithm defined by the EncryptionScheme attribute. The value of other(1) is used when a vendor-extension has been implemented for this attribute.";
    }
    typedef erm-connection-mode-type {
        type enumeration {
            enum other {
                value 1;
                description "The value of other is used when a vendor-extension has been implemented for this attribute.";
            }
            enum client {
                value 2;
            }
            enum server {
                value 3;
            }
            enum client-and-server {
                value 4;
            }
        }
        description "This attribute represents the type of TCP connection that is established by the CCAP. The value can be one of the following:
- 'other' indicates that a vendor-extension has been implemented for this attribute. - 'client' indicates that the CCAP has to initiate the TCP connection with the ERM. - 'server' indicates that the CCAP has to wait the TCP connection from the ERM. - 'client-and-server' indicates that both the CCAP or either the CCAP or the ERM can initiate the TCP connection.";
    }
    typedef integrated-server-type {
        type enumeration {
            enum other {
                value 1;
                description "The value of other is used when a vendor-extension has been implemented for this attribute.";
            }
            enum ftp {
                value 2;
            }
            enum http {
                value 3;
            }
            enum ssh {
                value 4;
            }
            enum telnet {
                value 5;
            }
            enum netconf {
                value 6;
            }
        }
        description "The type of server being configured on the CCAP. The value of other(1) is used when a vendor-extension has been implemented for this attribute. The CCAP SHOULD support a NETCONF server type. other(1), ftp(2), http(3), ssh(4), telnet(5), netconf(6)";
    }
    typedef policy-type {
        type enumeration {
            enum other {
                value 1;
                description "The value of other is used when a vendor-extension has been implemented for this attribute.";
            }
            enum login {
                value 2;
            }
            enum privileged-mode {
                value 3;
            }
        }
        description "This attribute is the first part of the key and configures the policy type for the specified protocol.";
    }
    typedef protocol-type {
        type enumeration {
            enum other {
                value 1;
                description "The value of other is used when a vendor-extension has been implemented for this attribute.";
            }
            enum radius {
                value 2;
            }
            enum tacacs-plus {
                value 3;
            }
            enum local-authentication {
                value 4;
            }
            enum none {
                value 5;
            }
        }
        description "This attribute is the second part of the key and represents the protocol used by the AAA server. The value of other(1) is used when a vendor-extension has been implemented for this attribute. ";
    }
    typedef timer-interval-type {
        type uint32 {
            range "5..2147483647";
        }
        units seconds;
        description "RIPv2 intervals.";
    }
    typedef send-version-type {
        type enumeration {
            enum other {
                value 1;
                description "The value of other is used when a vendor-extension has been implemented for this attribute.";
            }
            enum rip-version-1 {
                value 2;
            }
            enum rip-version-2 {
                value 3;
            }
            enum rip-version-1-and-2 {
                value 4;
            }
        }
        description "This attribute configures the version of the RIP protocol being used for this prefix. ";
    }
    typedef rip-auth-mode-type {
        type enumeration {
            enum other {
                value 1;
                description "The value of other is used when a vendor-extension has been implemented for this attribute.";
            }
            enum no-authentication {
                value 2;
            }
            enum simple-password {
                value 3;
            }
            enum md5 {
                value 4;
            }
        }
        description "This attribute configures the mode for authentication. [RFC 2453] defines this as simple password (type 2). The value of other(1) is used when a vendor-extension has been implemented for this attribute.";
        reference "RFC 2453";
    }
    typedef application-type {
        type enumeration {
            enum other {
                value 1;
                description "The value of other is used when a vendor-extension has been implemented for this attribute.";
            }
            enum host {
                value 2;
            }
            enum mta {
                value 3;
            }
            enum stb {
                value 4;
            }
            enum cm {
                value 5;
            }
            enum all {
                value 6;
            }
        }
        description "The device class for which this cable helper configuration applies.";
    }
    typedef igmp-version-type {
        type enumeration {
            enum other {
                value 1;
                description "The value of other is used when a vendor-extension has been implemented for this attribute.";
            }
            enum igmp-v1 {
                value 2;
            }
            enum igmp-v2-or-mld-v1 {
                value 3;
            }
            enum igmp-v3-or-mld-v2 {
                value 4;
            }
        }
        description "The version of MGMD. Value 2 applies to IGMPv1 routers only. Value 3 applies to IGMPv2 and MLDv1 routers, and value 4 applies to IGMPv3 and MLDv2 routers.";
    }
    typedef event-throttle-admin-state-type {
        type enumeration {
            enum unconstrained {
                value 1;
            }
            enum maintain-below-threshold {
                value 2;
            }
            enum stop-at-threshold {
                value 3;
            }
            enum inhibited {
                value 4;
            }
        }
        description "Refer to RFC 4639.";
        reference "RFC 4639";
    }
    typedef syslog-priority-type {
        type enumeration {
            enum emergency {
                value 1;
            }
            enum alert {
                value 2;
            }
            enum critical {
                value 3;
            }
            enum error {
                value 4;
            }
            enum warning {
                value 5;
            }
            enum notice {
                value 6;
            }
            enum information {
                value 7;
            }
            enum debug {
                value 8;
            }
        }
        description "See RFC 4639";
        reference "RFC 4639 docsDevEvPriority";
    }
    typedef syslog-reporting-type {
        type bits {
            bit local {
                position 0;
            }
            bit traps {
                position 1;
            }
            bit syslog {
                position 2;
            }
            bit local-volatile {
                position 3;
            }
            bit std-interface {
                position 4;
            }
        }
        description "See RFC 4639. The bit ordering has been changed from RFC 4639 to avoid gaps.";
        reference "RFC 4639 docsDevEvReporting";
    }
    typedef reg-detail-type {
        type bits {
            bit other {
                position 0;
            }
            bit initial-ranging {
                position 1;
            }
            bit ranging-auto-adj-complete {
                position 2;
            }
            bit start-eae {
                position 3;
            }
            bit start-dhcpv4 {
                position 4;
            }
            bit start-dhcpv6 {
                position 5;
            }
            bit dhcpv4-complete {
                position 6;
            }
            bit dhcpv6-complete {
                position 7;
            }
            bit start-config-file-download {
                position 8;
            }
            bit config-file-download-complete {
                position 9;
            }
            bit start-registration {
                position 10;
            }
            bit registration-complete {
                position 11;
            }
            bit bpi-init {
                position 12;
            }
            bit operational {
                position 13;
            }
        }
        description "Setting a bit representing a CM registration state will enable counting the number of times the CMTS determines that such CM reaches that state as the last state before failing to proceed further in the registration process and within the time interval considered for the CM registration trigger detection.";
    }
    typedef ranging-retry-trigger-type {
        type enumeration {
            enum consecutive-miss {
                value 1;
            }
            enum miss-ratio {
                value 2;
            }
        }
        description "This attribute selects the type of ranging retry trigger to be enable in the Diagnostic Log. A CM failure to perform ranging when a ranging opportunity is scheduled by the CMTS is counted as ranging miss. Ranging retry trigger can be configured to either look at consecutive ranging misses or ranging miss ratio over total number of station maintenance opportunities for a certain time period. Setting this object to 'consecutiveMiss' will select consecutive ranging misses as ranging retry trigger criteria. Setting this object to 'missRatio' will select ranging miss ratio as ranging retry criteria.";

    }
    typedef notif-ctrl-type {
        type bits {
            bit high-threshold-reached {
                position 0;
            }
            bit low-threshold-reached {
                position 1;
            }
            bit full {
                position 2;
            }
        }
        description "This attribute is used to enable diagnostic log related notifications. Setting bit 0 enables notification for reaching log size high threshold. Setting bit 1 enables notification for returning back to log size low threshold after reaching log size high threshold. Setting bit 2 enables notification for Diagnostic Log size full.";
    }
    typedef snmp-access-type {
        type enumeration {
            enum read-only {
                value 1;
            }
            enum read-write {
                value 2;
            }
        }
        description "Defines the type of access granted to the SNMP request.";
    }
    typedef subtree-view-inclusion-type {
        type enumeration {
            enum other {
                value 1;
                description "The value of other is used when a vendor-extension has been implemented for this attribute.";
            }
            enum included {
                value 2;
            }
            enum excluded {
                value 3;
            }
        }
        description "Indicates inclusion or exclusion of the subtree for the defined view.";
    }
    typedef notification-type {
        type enumeration {
            enum snmpv1-trap {
                value 1;
            }
            enum snmpv2c-trap {
                value 2;
            }
            enum snmpv2c-inform {
                value 3;
            }
        }
        description "Indicates the type of SNMP notification being sent. - 'snmpv1-trap': SNMP v1 trap - 'snmpv2c-trap': SNMP v2c trap - 'snmpv2c-inform': SNMP v2c Inform";
    }
    typedef address-prefix-len-type {
        type uint16 {
            range "0..2040";
        }
        description "This is based on RFC 4001 InetAddressPrefixLength.";
    }
    typedef snmp-tag-list-type {
        type string {
            length "0..255";
        }
        description "This data type is equivalent to the SnmpTagList.";
    }
    typedef ofdm-cyclic-prefix-type {
        type uint16 {
            range "192|256|512|768|1024";
        }
        description "This data type is defined to specify the five possible values for the length of cyclic prefix.  The cyclic prefix (in ?s) are converted into samples using the sample rate of 204.8 Msamples/s and is an integer multiple of: 1/64 * 20 ?s. The possible values come from table 7-1 in the D3.1 PHY Spec.";
    }
    typedef ofdma-cyclic-prefix-type {
        type uint16 {
            range "96|128|160|192|224|256|288|320|384|512|640";
        }
    }
    typedef ofdm-windowing-type {
        type uint16 {
            range "0|64|128|192|256";
        }
        description "This data type is defined to specify the five possible values for the windowing roll-off period.  The Roll-Off Period is given in ?s(microseconds). The possible values come from table 7-1 in the D3.1 PHY Spec.";
    }
    typedef ofdma-windowing-type {
        type uint16 {
            range "0|32|64|96|128|160|192|224";
        }
    }
    typedef subcarrier-spacing-type {
        type enumeration {
            enum other {
                value 1;
                description "The size in Hz of a subcarrier.";
            }
            enum 25khz {
                value 2;
            }
            enum 50khz {
                value 3;
            }
        }
    }
    typedef ofdm-modulation-type {
        type enumeration {
            enum other {
                value 1;
                description "The value of other is used when a vendor-extension has been implemented for this attribute.";
            }
            enum zero-value {
                value 2;
            }
            enum qpsk {
                value 3;
            }
            enum qam16 {
                value 4;
            }
            enum qam64 {
                value 5;
            }
            enum qam128 {
                value 6;
            }
            enum qam256 {
                value 7;
            }
            enum qam512 {
                value 8;
            }
            enum qam1024 {
                value 9;
            }
            enum qam2048 {
                value 10;
            }
            enum qam4096 {
                value 11;
            }
            enum qam8192 {
                value 12;
            }
            enum qam16384 {
                value 13;
            }
        }
        description "Defines the downstream OFDM modulation type.";
    }
    typedef ofdm-ncp-modulation-type {
        type enumeration {
            enum other {
                value 1;
                description "The value of other is used when a vendor-extension has been implemented for this attribute.";
            }
            enum qpsk {
                value 3;
            }
            enum qam16 {
                value 4;
            }
            enum qam64 {
                value 5;
            }
        }
        description "Defines the downstream OFDM NCP modulation type.";
    }
    typedef ofdma-modulation-type {
        type enumeration {
            enum other {
                value 1;
                description "The value of other is used when a vendor-extension has been implemented for this attribute.";
            }
            enum zero-value {
                value 2;
            }
            enum bpsk {
                value 3;
            }
            enum qpsk {
                value 4;
            }
            enum qam8 {
                value 5;
            }
            enum qam16 {
                value 6;
            }
            enum qam32 {
                value 7;
            }
            enum qam64 {
                value 8;
            }
            enum qam128 {
                value 9;
            }
            enum qam256 {
                value 10;
            }
            enum qam512 {
                value 11;
            }
            enum qam1024 {
                value 12;
            }
            enum qam2048 {
                value 13;
            }
            enum qam4096 {
                value 14;
            }
        }
        description "Defines the upstream OFDMA modulation type.";
    }
    extension extensionPoint {
        description "Hint to pyang to, optionally, define this as being 
                     of ext-type and to include ext-type in generated schema";
    }
    extension inlineType {
        description "Hint to pyang to, optionally, not to create a named complex
                     type, but rather leave this container or list as an in-line type.";
    }
    grouping vendor-extension-version {
    	container vendor-extension-version
    	{
	        leaf major-version {
	            type uint32;
	            mandatory true;
	            description "Major version provides the macro versioning number for each interface. Versions containing the same major version SHOULD provide backwards compatibility.";
	        }
	        leaf minor-version {
	            type int32;
	            mandatory true;
	            description "MinorVersion identifies incremental and backwards compatible updates to a major version.";
	        }
	        leaf micro-version {
	            type int32;
	            description "MicroVersion is usually for bug fixes, without changes in functionality.";
	        }
            container yang-ext {
                ccap:extensionPoint; //different pyang flags impact use of this hint
                description "node for vendor YANG extensions";
            }
    	}
    }
    grouping line-card-group {
        description "The line-card container contains configuration elements for a CCAP line card. There are several types of line cards defined for the CCAP: Downstream (DLC), Upstream (ULC), System Route Engine (SRE), a combined Upstream and Downstream line card, and an EPON line card.";
        reference 
            "CCAP Operations Support System Interface Specification
             CM-SP-CCAP-OSSI-I01-110930 LineCard section.";
        leaf line-card-name {
            type string;
            mandatory true;
            description "This attribute stores the name of the line card being configured.  ";
        }
        leaf admin-state {
            type admin-state-type;
            default down;
            description "This attribute configures the administrative state of the line card.";
        }
        leaf protected-by {
            type leafref {
                path "../../../slot/slot-number";
            }
            description "Line card redundancy or sparing is achieved with a protect relationship between two line cards.";
        }
    }
    grouping upstream-physical-channel-reference {
        description "A reference to an upstream physical channel.";
        leaf slot {
            type leafref {
                path "/ccap/chassis/slot/slot-number";
            }
            description "A reference to a slot number.";
        }
        leaf us-rf-port {
            type leafref {
                path "/ccap/chassis/slot[slot-number=current()/../slot]/us-rf-port/port-number";
            }
            description "A reference to a upstream RF port number.";
        }
        leaf upstream-physical-channel {
            type leafref {
                path "/ccap/chassis/slot[slot-number=current()/../slot]/us-rf-port[port-number=current()/../us-rf-port]/upstream-physical-channel/channel-index";
            }
            description "A reference to an upstream physical channel.";
        }
    }
    grouping upstream-logical-channel-reference {
        description "A reference to an upstream logical channel.";
        leaf slot {
            type leafref {
                path "/ccap/chassis/slot/slot-number";
            }
            description "A reference to a slot number.";
        }
        leaf us-rf-port {
            type leafref {
                path "/ccap/chassis/slot[slot-number=current()/../slot]/us-rf-port/port-number";
            }
            description "A reference to a upstream RF port number.";
        }
        leaf upstream-physical-channel {
            type leafref {
                path "/ccap/chassis/slot[slot-number=current()/../slot]/us-rf-port[port-number=current()/../us-rf-port]/upstream-physical-channel/channel-index";
            }
            description "A reference to an upstream physical channel.";
        }
        leaf upstream-logical-channel {
            type leafref {
                path "/ccap/chassis/slot[slot-number=current()/../slot]/us-rf-port[port-number=current()/../us-rf-port]/upstream-physical-channel[channel-index=current()/../upstream-physical-channel]/upstream-logical-channel/upstream-logical-channel-index";
            }
            description "A reference to an upstream logical channel.";
        }
    }
    grouping docsis-down-channel-reference {
        leaf slot {
            type leafref {
                path "/ccap/chassis/slot/slot-number";
            }
            description "A reference to a slot number.";
        }
        leaf ds-rf-port {
            type leafref {
                path "/ccap/chassis/slot[slot-number=current()/../slot]/ds-rf-port/port-number";
            }
            description "A reference to a downstream RF port number.";
        }
        leaf down-channel {
            type leafref {
                path "/ccap/chassis/slot[slot-number=current()/../slot]/ds-rf-port[port-number=current()/../ds-rf-port]/down-channel/channel-index";
            }
            description "A reference to a DOCSIS downstream channel index.";
        }
    }
    grouping video-down-channel-reference {
        leaf slot {
            type leafref {
                path "/ccap/chassis/slot/slot-number";
            }
            description "A reference to a slot number.";
        }
        leaf ds-rf-port {
            type leafref {
                path "/ccap/chassis/slot[slot-number=current()/../slot]/ds-rf-port/port-number";
            }
            description "A reference to a downstream RF port number.";
        }
        leaf down-channel {
            type leafref {
                path "/ccap/chassis/slot[slot-number=current()/../slot]/ds-rf-port[port-number=current()/../ds-rf-port]/down-channel/channel-index";
            }
            description "A reference to a video downstream channel index.";
        }
    }
    grouping ds-rf-port-reference {
        leaf slot {
            type leafref {
                path "/ccap/chassis/slot/slot-number";
            }
            description "Reference to the slot in which the downstream RF port resides.";
        }
        leaf ds-rf-port {
            type leafref {
                path "/ccap/chassis/slot[slot-number=current()/../slot]/ds-rf-port/port-number";
            }
            description "A reference to a downstream RF port number.";
        }
    }
    grouping us-rf-port-reference {
        leaf slot {
            type leafref {
                path "/ccap/chassis/slot/slot-number";
            }
            description "Reference to the slot in which the upstream RF port resides.";
        }
        leaf us-rf-port {
            type leafref {
                path "/ccap/chassis/slot[slot-number=current()/../slot]/us-rf-port/port-number";
            }
            description "A reference to an upstream RF port number.";
        }
    }
    grouping port-group {
        leaf port-number {
            type uint32;
            description "The port-number attribute of Port is a zero- or one-based index that sequentially numbers the physical ports of each derived type. For example, the Port numbers of 'DsRfPort' objects start at zero and increase to n-1.";
        }
        leaf admin-state {
            type admin-state-type;
            default down;
            description "This attribute configures the administrative state of the physical port.";
        }
        leaf up-down-trap-enabled {
            type boolean;
            default false;
            description "Indicates whether linkUp/linkDown SNMP traps should be generated for this interface.";
        }
    }
    grouping encryptor-group {
        leaf encryptor-index {
            type uint32;
            description "This key attribute identifies the instance of the encryptor.";
        }
        leaf ca-encryptor-type {
            type ca-encryptor-type-type;
            mandatory true;
            description "This enumeration defines the type of CA encryption the Encryptor uses. ";
        }
        leaf ecm-timeout {
            type uint16;
            units seconds;
            default 10;
            description "This attribute configures the number of seconds that a CCAP will wait to get a response from a ECMG before switching to the redundant unit.";
        }
        leaf clear-stream-timeout {
            type uint16;
            units seconds;
            default 10;
            description "This configured attribute defines the number of seconds a given stream may be sent in the clear when the stream is configured to be encrypted.  If this timer expires and the session has not received any encryption information from the ECMG, the CCAP MUST discontinue forwarding this stream.";
        }
        list ecmg-usage {
            key ecmg-usage-index;
            min-elements 1;
            description "The ecmg-usage object provides for the configuration of multiple encryption sessions. It is an intermediate object that provides linkages between Encryptor objects and the ECMG(s) associated with those encrypted streams.";
            leaf ecmg-usage-index {
                type uint32;
                description "This is an index for an instance of this object. ecmg-usage-index is a pointer to an active ECMG that can be used for any program session that requires encryption as long as the CAS identifier matches.";
            }
            leaf priority {
                type uint32;
                mandatory true;
                description "This is the configured selection priority for any program session that requires encryption when multiple ECMGs with the same CAS identifier are active. The ECMG with the lowest number should be selected first.";
            }
            leaf ecmg-ref {
                type leafref {
                    path "/ccap/video/ecmg/ecm-index";
                }
                description "A reference to the index of an ecmg instance.";
            }
            container yang-ext {
                ccap:extensionPoint; //different pyang flags impact use of this hint
                description "node for vendor YANG extensions";
            }
        }
    }
    grouping mac-domain-configuration-group {
        description "The mac-domain-configuration-group configures the MAC domain attributes used by DOCSIS and EPON MAC domains.";
        leaf mac-domain-name {
            type string;
            description "The name of the MacDomain.";
        }
        leaf ip-provisioning-mode {
            type ip-prov-mode-type;
            mandatory true;
            description
                "This attribute configures the IP provisioning mode for a MAC Domain.
                 When this attribute is set to 'ipv4-only' the CM will acquire a single IPv4 address for the CM management stack.
                 When this attribute is set to 'ipv6-only' the CM will acquire a single IPv6 address for the CM management stack.
                 When this attribute is set to 'alternate' the CM will acquire a single IPv6 address for the CM management stack and, if failures occur, the CM will fall back to provisioning and operation with an IPv4 address.
                 When this attribute is set to 'dual-stack' the CM will acquire both an IPv6 and IPv4 address for provisioning and operation.";
            reference 
                "DOCSIS 3.0 Operations Support System Interface Specification
                 CM-SP-OSSIv3.0-I15-110623 MdCfg Object Section.";
        }
        leaf admin-state {
            type admin-state-type;
            default down;
            description "This attribute configures the administrative state of the mac-domain.";
        }
        leaf up-down-trap-enabled {
            type boolean;
            default true;
            description "Indicates whether linkUp/linkDown SNMP traps should be generated for this interface.";
        }
    }
    grouping down-channel-group {
        leaf channel-index {
            type uint32;
            description "This key identifies a channel on a specific RF Port.";
        }
        leaf admin-state {
            type admin-state-type;
            default down;
            description "This attribute represents the administrative status of the channel. For downstream channels, Setting the value to down(3) results in the channel being muted, and the value of testing(4) is used to generate a continuous test wave on this QAM channel.";
        }
        leaf up-down-trap-enabled {
            type boolean;
            default true;
            description "Indicates whether linkUp/linkDown SNMP traps should be generated for this interface.";
        }
        leaf power-adjust {
            type int16;
            units tenthdb;
            default 0;
            description "This attribute represents the power gain for the channel. It is expressed in TenthdB.";
        }
        leaf frequency {
            type uint32;
            units hertz;
            mandatory true;
            description "This attribute specifies the center frequency of the channel. It is expressed in Hertz. The CCAP MUST NOT allow the frequency of any DownChannel instances to overlap on a given downstream RF port.";
        }
        leaf rf-mute {
            type boolean;
            default false;
            description "This attribute configures the mute state for the specific DownChannel. If set to true, the ifOperStatus of the VideoDownChannel or DocsisDownChannel associated with this instance of DownChannel is set to 'down'. If set to false, no muting takes place. Operation while muted is described in [DRFI]";
            reference "DOCSIS Downstream RF Interface Specification CM-SP-DRFI-I11-110210.";
        }
        leaf qam-alias {
            type string;
            description "This attribute represents the name of the QAM channel and is equivalent to the ifAlias object in the if-MIB.";
        }
        leaf errp-advertising {
            type boolean;
            default true;
            description "This attribute represents the ERRP advertisement state of the QAM channel. If set to true, the QAM channel is advertised; otherwise it is not advertised. This is primarily useful when statically configuring the QAM channels and when the QAM channel is not made part of the ERM channel list. This attribute is optional for DocsisDownChannel.";
        }
        choice erm-channel-config {
            case erm-managed {
                    description "This optional configuration object allows for the configuration of the needed parameters that are communicated to an ERM for a given DownChannel object instance.";
                    leaf input-map-group-name {
                        type string;
                        mandatory true;
                        description "This attribute represents the address field in the WithdrawnRoute and ReachableRoutes ERRP attributes. This attribute is optional for DocsisDownChannel.";
                    }
                    leaf phy-lock-parameters {
                        type bits {
                            bit frequency {
                                position 0;
                            }
                            bit bandwidth {
                                position 1;
                            }
                            bit power {
                                position 2;
                            }
                            bit modulation {
                                position 3;
                            }
                            bit interleaver {
                                position 4;
                            }
                            bit j83annex {
                                position 5;
                            }
                            bit symbol-rate {
                                position 6;
                            }
                            bit mute {
                                position 7;
                            }
                        }
                        default " ";
                        description "This attribute represents the PHY parameters Lock state of the QAM channels for DEPI-initiated PHY parameters updates.";
                    }
                    leaf allocation-type {
		                type downstream-allocation-type;
                        default any;
                        description "This attribute defines the services this specific DownChannel instance can be allocated to.";
                    }
                    list encryption-capability {
                        key encryption-capability-index;
                        min-elements 0;
                        max-elements 3;
                        description "The EncryptionCapability object defines one encryption option of the Encryptor that needs to be reported to the ERM. There can be up to three EncryptionCapability objects per QAM. In return, the ERM is expected to create dynamic sessions using one of the reported encryption options.";
                        leaf encryption-capability-index {
                            type uint32;
                            mandatory true;
                            description "This attributes assigns a unique identifier to this instance of the EncryptionCapability object.";
                        }
                        leaf ca-encryptor {
                            type ca-encryptor-type-type;
                            mandatory true;
                            description "This enumeration defines the type of CA encryption the Encryptor uses. The value of other(1) is used when a vendor-extension has been implemented for this attribute.";
                        }
                        leaf encryption-scheme {
                            type encryption-scheme-type;
                            mandatory true;
                            description "This attribute defines the encryption algorithms applicable to the CA encryption defined by the CaEncryptor attribute. The value of other(1) is used when a vendor-extension has been implemented for this attribute.";
                        }
                        leaf key-length {
                            type uint32;
                            mandatory true;
                            description "This attribute defines the key length applicable to the algorithm defined by the EncryptionScheme attribute.";
                        }
                        container yang-ext {
                            ccap:extensionPoint; //different pyang flags impact use of this hint
                            description "node for vendor YANG extensions";
                        }
                    }
                    leaf erm-name {
                        type leafref {
                            path "/ccap/video/erm-registration/erm-name";
                        }
                        mandatory true;
                        description "The ERM that manages this down channel.";
                    }
                    container yang-ext5 {
                        ccap:extensionPoint; //different pyang flags impact use of this hint
                        description "node for vendor YANG extensions";
                    }
            }
            case yang-choice-ext {
                ccap:extensionPoint; //different pyang flags impact use of this hint
                description "node for vendor YANG extensions";
            }
        }
    }
    grouping video-down-channel-group {
        leaf video-output-tsid {
            type uint16;
            mandatory true;
            description "This attribute specifies the output TSID of the channel. This attribute is required for a VideoDownChannel. The TSID is globally unique per CCAP. Replicated output streams share the same OutputTsid.";
        }
    }
    grouping docsis-down-channel-group {
        leaf id {
            type uint32;
            description "Unique identifier per mac-domain for the docsis-down-channel. Used in DOCSIS messages. A value of 0 (zero) means that the CCAP will automatically assign the Id.";
        }
        leaf provisioned-attribute-mask {
            type attribute-mask-type;
            description "This attribute contains Provisioned Attribute Mask of non-bonded service flow assignment to this channel.";
        }
        leaf docsis-output-tsid {
            type uint16;
            default 0;
            description "This optional attribute specifies the output TSID of the channel. This attribute is optional for DocsisDownChannel. The TSID is globally unique per CCAP.  Replicated output streams share the same OutputTsid.

";
        }
    }
    grouping ds-rf-port-group {
        leaf rf-mute {
            type boolean;
            default false;
            description "The attribute rf-mute refers to a diagnostic state defined in the DOCSIS RF Interface (DRFI) Specification. Muting an RF port affects only the output power and does not impact the operational status of any channel on the port.  ";
            reference "DOCSIS Downstream RF Interface Specification CM-SP-DRFI-I11-110210.";
        }
        leaf base-channel-power {
            type int32;
            units TenthdBmV;
            mandatory true;
            description "This attribute configures the base output power  for each single DownChannel on the DsRfPort.  The value is expressed in dBmV in units of Tenthdb. The default value is vendor specific. Acceptable power ranges for this attribute are defined in the Power per Channel CMTS or EQAM section of [DRFI].
";
            reference "DOCSIS Downstream RF Interface Specification CM-SP-DRFI-I11-110210 Power per Channel CMTS or EQAM section";
        }
        uses port-group;
        list down-channel {
            key channel-index;
            unique frequency;
            max-elements 158;
            description "A list of down channels.";
            uses down-channel-group;
            choice channel-type {
                mandatory true;
                case docsis {
                        description 
                            "The docsis-down-channel object is a down-channel used exclusively for DOCSIS. The down-channel is its generalization. 
                             The docsis-down-channel object is a specialization of down-channel."; 
                        uses docsis-down-channel-group;
                        leaf docsis-phy-profile-index {
                            type leafref {
                                path "/ccap/chassis/docsis-phy-profile/phy-index";
                            }
                            description "A reference to a Docsis physical parameters profile. The default for this index is vendor-dependent; it must default to an index that is always present in the phy-profile list.";
                       }
                       container yang-ext1 {
                           ccap:extensionPoint; //different pyang flags impact use of this hint
                           description "node for vendor YANG extensions";
                       }
                }
                case video {
                        description "The video-down-channel object is a down-channel used exclusively for video channel configuration";
                        uses video-down-channel-group;
                        leaf video-phy-profile-index {
                            type leafref {
                                path "/ccap/chassis/video-phy-profile/phy-index";
                            }
                            description "A reference to a video physical parameters profile. The default for this index is vendor-dependent; it must default to an index that is always present in the phy-profile list.";
                        }
                        container yang-ext2 {
                            ccap:extensionPoint; //different pyang flags impact use of this hint
                            description "node for vendor YANG extensions";
                        }
                }
                case yang-choice-ext2 {
                    ccap:extensionPoint; //different pyang flags impact use of this hint
                    description "node for vendor YANG extensions";
                }
            }
            container yang-ext {
                ccap:extensionPoint; //different pyang flags impact use of this hint
                description "node for vendor YANG extensions";
            }
        }
        list ofdm-exclusions {
            key start-freq;
            leaf start-freq {
                type uint32 {
                    range "108000000..177000000";
                }
                units Hertz;
                description "The lowest frequency of the exclusion zone";
            }
            leaf end-freq {
                type uint32 {
                    range "108000000..177000000";
                }
                mandatory true;
                units Hertz;
                description "The highest frequency of the exclusion zone";
            }
            container yang-ext {
                ccap:extensionPoint; //different pyang flags impact use of this hint
                description "node for vendor YANG extensions";
            }
        }
        list ofdm-ncp-exclusions {
            key start-freq;
            leaf start-freq {
                type uint32 {
                    range "108000000..177000000";
                }
                units Hertz;
                description "The lowest frequency of the NCP exclusion zone";
            }
            leaf end-freq {
                type uint32 {
                    range "108000000..177000000";
                }
                mandatory true;
                units Hertz;
                description "The highest frequency of the NCP exclusion zone";
            }
            container yang-ext {
                ccap:extensionPoint; //different pyang flags impact use of this hint
                description "node for vendor YANG extensions";
            }
        }
        list ofdm-channel {
            key ofdm-channel-index;
            max-elements 16;
            description "A list of OFDM down channels.";
            leaf ofdm-channel-index {
                type uint32;
                description "This key identifies an OFDM channel on a specific RF Port.";
            }
            leaf admin-state {
                type admin-state-type;
                default down;
                description "This attribute represents the administrative status of the channel. For downstream channels, Setting the value to down(3) results in the channel being muted, and the value of testing(4) is used to generate a continuous test wave on this QAM channel.";
            }
            leaf docs-chan-id {
                type uint32;
                default 0;
                description "Unique identifier per mac-domain for the docsis-down-channel. Used in DOCSIS messages. A value of 0 (zero) means that the CCAP will automatically assign the Id.";
            }
            leaf lower-edge-freq {
                type uint32 {
                    range "108000000..1770000000";
                }
                units Hertz;
                mandatory true;
                description "This attribute specifies the lower edge frequency of the OFDM channel. It is expressed in Hertz.";
           }
            leaf upper-edge-freq {
                type uint32 {
                    range "132000000..1794000000";
                }
                units Hertz;
                mandatory true;
                description "This attribute specifies the upper edge frequency of the OFDM channel. It is expressed in Hertz.";
            }
            leaf plc-freq {
                type uint32 {
                    range "108000000..1770000000";
                }
                units Hertz;
                mandatory true;
                description "This attribute specifies the lower edge frequency of the PLC of the OFDM channel. It is expressed in Hertz.";
            }
            leaf cyclic-prefix {
                type ofdm-cyclic-prefix-type;
                units Microseconds;
                mandatory true;
                description "Cyclic prefix enables the receiver to overcome the effects of inter-symbol-interference and intercarrier-interference caused by micro-reflections in the channel.The cyclic prefix is converted into samples using the sample rate of 204.8 Msamples/s and is an integer multiple of: 1/64 * 20 ?s.";
            }
            leaf rolloff-period {
                type ofdm-windowing-type;
                mandatory true;
                description "Windowing maximizes channel capacity by sharpening the edges of the spectrum of the Ofdm signal. For windowing purposes another segment at the start of the IDFT output is appended to the end of the IDFT output -the roll-off postfix (RP).  There are five possible values for the (RP), and the choice depends on the bandwidth of the channel and the number of exclusion bands within the channel. A larger RP provides sharper edges in the spectrum of the Ofdm signal; however, there is a time vs. frequency trade-off. Larger RP values reduce the efficiency of transmission in the time domain, but because the spectral edges are sharper, more useful subcarriers appear in the frequency domain. There is an optimum value for the RP that maximizes capacity for a given bandwidth and/or exclusion band scenario.";
            }
            leaf time-interleaver-depth {
                type uint8 {
                    range "1..32";
                }
                units Samples;
                mandatory true;
                description "The number of samples for the Ofdm Downstream channel.  This is limited to a maximum of 16 samples for and 32 samples for 4k FFT and 8k FFT respectively.";
            }
            leaf subcarrier-spacing {
                type subcarrier-spacing-type;
                mandatory true;
                description "The width of an OFDM channel.";
            }
            leaf up-down-trap-enabled {
                type boolean;
                default true;
                description "Indicates whether linkUp/linkDown SNMP traps should be generated for this interface.";
            }
            leaf num-of-pilots {
                type uint32;
                mandatory true;
                description "This attribute indicates the number of pilots configured for the downstream channel. This includes the sum of scattered + continuous pilots across the entire Ofdm downstream channel.";
            }
            leaf subcarrier-zero-freq {
                type uint32 {
                    range "108000000..177000000";
                }
                units Hertz;
                mandatory true;
                description "The frequency of subcarrier 0.";
            }
            leaf ncp-modulation-order {
                type ofdm-ncp-modulation-type;
                mandatory true;
            }
            leaf lower-guard-band {
                type uint32;
                description "";
            }
            leaf upper-guard-band {
                type uint32;
                description "";
            }
            list ofdm-profile {
                key ofdm-profile-index;
                max-elements 17;
                description "A list of OFDM profiles for this channel.";
                leaf ofdm-profile-index {
                     type uint8 {
                         range "1..16|255";
                     }
                     description "255 is reserved for the PLC profile. Vendors may auto-configure profiles.";
                }
                leaf ofdm-modulation-default {
                    type ofdm-modulation-type;
                    mandatory true;
                }
                list ofdm-subcarrier {
                    key start-frequency;
                    description "An exception to the default modulation for this profile.";
                    leaf start-frequency {
                        type uint32 {
                            range "108000000..1770000000";
                        }
                        description "If there is no actual range (e.g., because end-frequency is omitted), and this frequency matches the edge of a subcarrier, then only the subcarrier whose lower edge matches this frequency is used.";
                    }
                    leaf end-frequency {
                        type uint32 {
                            range "108000000..1770000000";
                        }
                        description "Optional; if omitted, then this exception is just for the subcarrier matching the start-frequency.";
                    }
                    leaf skip {
                        type boolean;
                        default false;
                        description "This attribute indicates if the configuration applies to contiguous subcarriers or if it applies to every other subcarrier.";
                    }
                    leaf ofdm-main-modulation {
                        type ofdm-modulation-type;
                        mandatory true;
                        description "If skip is false, the modulation for this range of subcarriers. If skip is true, the modulatiion for the odd-numbered subcarriers in the frequency range.";
                    }
                    leaf ofdm-skip-modulation {
                        type ofdm-modulation-type;
                        description "Ignored if skip is false. If skip is true, the modulation of the even-numbered subcarriers in the frequency range.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
    }
    grouping us-rf-port-group {
        uses port-group;
        list upstream-physical-channel {
            key channel-index;
            unique frequency;
            description 
                "The upstream-physical-channel object represents DOCSIS operation on a single upstream center frequency at a particular channel width. 
                 Since CCAP is expected to operate with only DOCSIS 2.0 or later upstream channels, at least one UpstreamLogicalChannel object (ifType 205) is needed to be instantiated to operate within an upstream-physical-channel.  
                 This object differs from the same object in DOCSIS in that the desired input power is now set at the upstream-physical-channel and not on a per-LogicalUpstreamChannel instance. If the target receive power level for an individual logical channel under a physical channel is desired to be different than the target power level for the physical channel, this can be configured using the PowerLevelAdjust attribute of the UpstreamLogicalChannel object.";
            leaf channel-index {
                type uint32;
                description "This key identifies a channel on a specific RF Port.";
            }
            leaf admin-state {
                type admin-state-type;
                default down;
                description "This attribute represents the administrative status of the channel. For downstream channels, Setting the value to down(3) results in the channel being muted, and the value of testing(4) is used to generate a continuous test wave on this QAM channel.";
            }
            leaf up-down-trap-enabled {
                type boolean;
                default true;
                description "Indicates whether linkUp/linkDown SNMP traps should be generated for this interface.";
            }
            leaf frequency {
                type uint32 {
                    range "5000000..85000000";
                }
                units Hertz;
                mandatory true;
                description "This attribute configures the center frequency of the upstream-physical-channel, in Hertz. As of DOCSIS 3.0, the minimum permitted value is the center frequency such that the lower channel edge is 5000000 Hz and the maximum permitted value is the center frequency at which the upper channel edge is 85000000 Hz.  This attribute corresponds to the docsIfUpChannelFrequency object of DOCS-IF-MIB [RFC 4546]. ";
                reference "RFC 4546 DOCS-IF-MIB";
            }
            leaf width {
	        type us-channel-width;
                mandatory true;
                description "This attribute configures the width of the upstream-physical-channel, in Hertz.  The only permitted values as of DOCSIS 3.0 are 1600000, 3200000, and 6400000. The CCAP may support the narrower channel widths 200000, 400000 and 800000KHz.  This attribute corresponds to the docsIfUpChannelFrequency object of DOCS-IF-MIB [RFC 4546].";
                reference "RFC 4546 DOCS-IF-MIB";
            }
            leaf power-level {
                type uint32;
                units TenthdBmV;
                mandatory true;
                description "This attribute configures the desired input power level, in TenthdBmV, common for all upstream logical channels associated with this physical channel instance. The power level for individual logical channel can be deviated from the common power level through configuration of PowerLevelAdjust attribute.";
            }
            list upstream-logical-channel {
                key upstream-logical-channel-index;
                description "A list of upstream logical channels.";
                min-elements 1;
                uses upstream-logical-channel-group;
                choice logical-channel-type {
                    mandatory true;
                    case scdma-logical-channel {
                            description 
                                "This configuration object is constructed from the SCDMA fields of the docsIfUpstreamChannelTable defined in [RFC 4546] and the DOCS-IFEXT2-MIB defined in Annex H of [OSSIv3.0].
                                 The scdma object is an optional grouping of additional parameters to an UpstreamLogicalChannel that is defined only for UpstreamLogicalChannel objects that reference an SCDMA modulation profile.";
                            reference 
                                "DOCSIS 3.0 Operations Support System Interface Specification
                                 CM-SP-OSSIv3.0-I15-110623 Requirements for DOCS-IFEXT2-MIB Annex; RFC 4546 docsIfUpstreamChannelTable.";
                            leaf active-codes {
                                type uint32;
                                description "This attribute configures the number of active codes used in this channel.  Note that legal values from 64..128 are required to be non-prime. Valid values are 0|64..66| 68..70| 72| 74..78| 80..82| 84..88| 90..96| 98..100|102| 104..106|108 |110..112|114..126|128.";
                            }
                            leaf codes-per-slot {
                                type uint32;
                                description "Applicable for SCDMA channel types only. The configured number of SCDMA codes per mini-slot.";
                            }
                            leaf frame-size {
                                type uint32;
                                description "Applicable for SCDMA channel types only. The configured SCDMA frame size in units of spreading intervals.";
                            }
                            leaf hopping-seed {
                                type uint32;
                                description "Applicable for SCDMA channel types only. 15-bit seed used for code hopping sequence initialization. Returns zero for non-SCDMA channel types.";
                            }
                            leaf msc-state {
                                type msc-state-type;
                                default channel-disabled;
                                description "Indicates the state of the Maximum Scheduled Codes feature for an individual logical channel on the CCAP.";
                                reference 
                                    "DOCSIS 3.0 Operations Support System Interface Specification
                                     CM-SP-OSSIv3.0-I15-110623 Requirements for DOCS-IFEXT2-MIB Annex.";
                            }
                            leaf msc-minimum-value {
                                type uint8 {
                                    range "4..128";
                                }
                                units codes;
                                default 4;
                                description "When Maximum Scheduled Codes is enabled, instructs the CCAP to assign cable modems MSC values no less than this value.";
                            }
                            container yang-ext1 {
                                ccap:extensionPoint; //different pyang flags impact use of this hint
                                description "node for vendor YANG extensions";
                            }
                    }
                    case tdma-logical-channel {
                            description "This configuration object is a specialization of the docsIfUpstreamChannelTable defined in [RFC 4546] for TDMA logical channels.
";
                            reference 
                                "DOCSIS 3.0 Operations Support System Interface Specification
                                 CM-SP-OSSIv3.0-I15-110623 Requirements for DOCS-IFEXT2-MIB Annex; RFC 4546 docsIfUpstreamChannelTable.";
                            container yang-ext2 {
                                ccap:extensionPoint; //different pyang flags impact use of this hint
                                description "node for vendor YANG extensions";
                            }
                    }
                    case atdma-logical-channel {
                            description "This configuration object is a specialization of the docsIfUpstreamChannelTable defined in [RFC 4546] for ATDMA logical channels.

";
                            reference 
                                "DOCSIS 3.0 Operations Support System Interface Specification
                                 CM-SP-OSSIv3.0-I15-110623 Requirements for DOCS-IFEXT2-MIB Annex; RFC 4546 docsIfUpstreamChannelTable.";
                            container yang-ext3 {
                                ccap:extensionPoint; //different pyang flags impact use of this hint
                                description "node for vendor YANG extensions";
                            }
                    }
                    case tdma-and-atdma-logical-channel {
                            description "This configuration object is a specialization of the docsIfUpstreamChannelTable defined in [RFC 4546] for mixed TDMA/ATDMA logical channels.

";
                            reference 
                                "DOCSIS 3.0 Operations Support System Interface Specification
                                 CM-SP-OSSIv3.0-I15-110623 Requirements for DOCS-IFEXT2-MIB Annex; RFC 4546 docsIfUpstreamChannelTable.";
                            container yang-ext4 {
                                ccap:extensionPoint; //different pyang flags impact use of this hint
                                description "node for vendor YANG extensions";
                            }
                    }
                    case yang-choice-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
        list ofdma-exclusions {
            key start-freq;
            leaf start-freq {
                type uint32 {
                    range "5000000..197600000";
                }
                units Hertz;
                description "The lowest frequency of the exclusion zone. Minimum channel size is 6.4 MHz.";
            }
            leaf end-freq {
                type uint32 {
                    range "11400000..204000000";
                }
                mandatory true;
                units Hertz;
                description "The highest frequency of the exclusion zone. Minimum channel size is 6.4 MHz.";
            }
            container yang-ext {
                ccap:extensionPoint; //different pyang flags impact use of this hint
                description "node for vendor YANG extensions";
            }
        }
        list ofdma-channel {
            key ofdma-channel-index;
            description "List of OFDMA channels on this RF port.";
            leaf ofdma-channel-index {
                type uint16;
                description "This key identifies an OFDMA channel on a specific RF Port.";
            }
            leaf admin-state {
                type admin-state-type;
                default down;
                description "This attribute represents the administrative status of the channel. For downstream channels, Setting the value to down(3) results in the channel being muted, and the value of testing(4) is used to generate a continuous test wave on this QAM channel.";
            }
            leaf up-down-trap-enabled {
                type boolean;
                default true;
                description "Indicates whether linkUp/linkDown SNMP traps should be generated for this interface.";
            }
            leaf lower-edge-freq {
                type uint32 {
                    range "5000000..197600000";
                }
                units Hertz;
                mandatory true;
                description "This attribute defines the lower frequency for the US Channel.";
            }
            leaf upper-edge-freq {
                type uint32 {
                    range "11400000..204000000";
                }
                units Hertz;
                mandatory true;
                 description "This attribute defines the upper frequency for the US Channel.";
           }
            leaf channel-id {
                type uint32;
                default 0;
                description "This attribute permits an operator to optionally configure the upstream channel ID signaled in the DOCSIS protocol for the UpstreamLogicalChannel. If zero, CMTSs automatically assign the DocsisUpChannelId, and this attribute is only read. An operator can create or update this attribute with a non-zero value to force the CCAP to use the configured DOCSIS channel ID. A unique configured value exists within the MacDomain to which the upstream-physical-channel containing this UpstreamLogicalChannel is associated.";
            }
            leaf provisioned-attribute-mask {
                type attribute-mask-type;
                mandatory true;
                description "This attribute configures the 32-bit Provisioned Attribute Mask for the UpstreamLogicalChannel. This is used by a CCAP to control how upstream service flows are assigned to the UpstreamLogicalChannel.";
            }
            leaf ranging-backoff-start {
                type uint8 {
                    range "0..15";
                }
            mandatory true;
                description "This attribute is the initial random back-off window to use when retrying Ranging Requests. It is expressed as a power of 2. A value of 16 at the CCAP indicates that a proprietary adaptive retry mechanism is to be used.";
            }
            leaf ranging-backoff-end {
                type uint8 {
                    range "0..15";
                }
                mandatory true;
                description "This attribute is the final random back-off window to use when retrying Ranging Requests. It is expressed as a power of 2. A value of 16 at the CCAP indicates that a proprietary adaptive retry mechanism is to be used.";
            }
            leaf transmit-backoff-start {
                type uint8 {
                    range "0..15";
                }
                mandatory true;
                description "The initial random back-off window to use when retrying transmissions. Expressed as a power of 2. A value of 16 at the CCAP indicates that a proprietary adaptive retry mechanism is to be used. See the associated conformance object for write conditions and limitations.";
            }
            leaf transmit-backoff-end {
                type uint8 {
                    range "0..15";
                }
                mandatory true;
                description "The final random back-off window to use when retrying transmissions. Expressed as a power of 2. A value of 16 at the CCAP indicates that a proprietary adaptive retry mechanism is to be used. See the associated conformance object for write conditions and limitations.";
            }
            leaf auto-ofdma-profile-cfg {
                type boolean;
                default false;
                description "Whetheror not the CCAP will internally provision the PHY parameters for this OFDMA channel. What it means to internally provision PHY parameters is vendor specific.";
            }
            leaf target-rx-power {
                type uint32;
                units tenthdBmV;
                description "";
            }
            leaf ofdma-chan-profile {
                type leafref {
                    path "/ccap/docsis/ofdma-profile/ofdma-profile-index";
                }
                description "A reference to an OFDMA channel profile.";
            }

            list ofdma-chan-data-iuc {
                key data-iuc;
                description "Data IUC with one or more exceptions to default minislot pilot pattern and/or minislot modulation defined by the channel profile.";
                leaf data-iuc {
                    type uint8 {
                        range "5|6|9|10|11|12|13";
                    }
                }
                list ofdma-minislot-cfg {
                    key lower-freq;
                    min-elements 1;
                    leaf lower-freq {
                        type uint32 {
                            range "500000..204000000";
                        }
                        description "This attribute defines the start frequency where the minislots will use the pilot pattern and modulation as specified by this object, instead of the defaults for the channel. LowerFreq must be within the frequencies allotted to the channel.";
                    }
                    leaf upper-freq {
                        type uint32 {
                            range "500000..204000000";
                        }
                        description "This attribute defines the end frequency where the minislots will use the pilot pattern and modulation as specified by this object, instead of the defaults for the channel. The UpperFreq value must be greater than or equal the LowerFreq value. UpperFreq must be within the frequencies allotted to the channel.";
                    }
                    leaf minislot-pilot-pattern {
                        type uint8 {
                            range "1..14";
                        }
                        mandatory true;
                        description "This attribute defines the pilot pattern for the frequency range. All minislots in the frequency range have this pilot pattern. Channels using 2k mode are restricted to patterns 1-7, while channels using 4k mode are restricted to patterns 8-14 ([PHY3.1], section 7.4.16).";
                    }
                    leaf minislot-modulation {
                        type ofdma-modulation-type;
                        mandatory true;
                        description "This attribute defines the modulation for the frequency range. All minislots in the frequency range have this modulation.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
    }
    grouping down-channel-phy-params-group {
        leaf phy-index {
            type uint32;
            description "The index of the profile.";
        }                
        leaf modulation {
            type qam-modulation-type;
            default qam256;
            description "Defines the modulation type used. The value of other(1) is used when a vendor-extension has been implemented for this attribute.";
        }
        leaf interleaver-depth {
            type interleaver-depth-type;
            default fecI128J1;
            description 
                "This attribute represents the interleaving depth or operation mode of the interleaver. The value of other(1) is used when a vendor-extension has been implemented for this attribute.
                 This attribute is ignored when downstream-phy-standard has a value other than j83annexB.";
        }
        leaf downstream-phy-standard {
            type downstream-phy-type;
            default j83annexB;
            description "This attribute specifies the standard supported by the QAM channel. A value of 'dvbc' corresponds to J.83 Annex A. The value of other(1) is used when a vendor-extension has been implemented for this attribute";
        }
    }
    grouping upstream-logical-channel-group {
        leaf upstream-logical-channel-index {
            type uint32;
            description "The channel index for an upstream logical channel.";
        }
        leaf admin-state {
            type admin-state-type;
            default down;
            description "This attribute configures the administrative state of the upstream logical channel.";
        }
        leaf up-down-trap-enabled {
            type boolean;
            default false;
            description "Indicates whether linkUp/linkDown SNMP traps should be generated for this interface.";
        }
        leaf channel-id {
            type uint32;
            default 0;
            description "This attribute permits an operator to optionally configure the upstream channel ID signaled in the DOCSIS protocol for the UpstreamLogicalChannel. If zero, CMTSs automatically assign the DocsisUpChannelId, and this attribute is only read. An operator can create or update this attribute with a non-zero value to force the CCAP to use the configured DOCSIS channel ID. A unique configured value exists within the MacDomain to which the upstream-physical-channel containing this UpstreamLogicalChannel is associated.";
        }
        leaf slot-size {
            type uint32;
            mandatory true;
            description "This attribute configures the number of 6.25 microsecond ticks in each upstream mini-slot for the UpstreamLogicalChannel. This attribute may have different values for the different UpstreamLogicalChannel objects on the same upstream-physical-channel. This attribute is applicable to TDMA and ATDMA channel types only; its value is read and written as zero for SDCMA type channels.";
        }
        leaf ranging-backoff-start {
            type uint8 {
                range "0..16";
            }
            mandatory true;
            description "This attribute is the initial random back-off window to use when retrying Ranging Requests. It is expressed as a power of 2. A value of 16 at the CCAP indicates that a proprietary adaptive retry mechanism is to be used.";
        }
        leaf ranging-backoff-end {
            type uint8 {
                range "0..16";
            }
            mandatory true;
            description "This attribute is the final random back-off window to use when retrying Ranging Requests. It is expressed as a power of 2. A value of 16 at the CCAP indicates that a proprietary adaptive retry mechanism is to be used.";
        }
        leaf transmit-backoff-start {
            type uint8 {
                range "0..16";
            }
            mandatory true;
            description "The initial random back-off window to use when retrying transmissions. Expressed as a power of 2. A value of 16 at the CCAP indicates that a proprietary adaptive retry mechanism is to be used. See the associated conformance object for write conditions and limitations.";
        }
        leaf transmit-backoff-end {
            type uint8 {
                range "0..16";
            }
            mandatory true;
            description "The final random back-off window to use when retrying transmissions. Expressed as a power of 2. A value of 16 at the CCAP indicates that a proprietary adaptive retry mechanism is to be used. See the associated conformance object for write conditions and limitations.";
        }
        leaf pre-equalization-enable {
            type boolean;
            mandatory true;
            description "This attribute enables pre-equalization on the UpstreamLogicalChannel when its value is true, or disables pre-equalization when its value is false.";
        }
        leaf provisioned-attribute-mask {
            type attribute-mask-type;
            mandatory true;
            description "This attribute configures the 32-bit Provisioned Attribute Mask for the UpstreamLogicalChannel. This is used by a CCAP to control how upstream service flows are assigned to the UpstreamLogicalChannel.";
        }
        leaf power-level-adjust {
            type uint32;
            units tenthdbm;
            default 0;
            description "This attribute configures the adjustment from the common power level configured for the physical US channel in TenthdB. The sum of the PowerLevel and PowerLevelAdjust determines the expected input power level for the logical channel. If the CCAP does not support the ability to set the PowerLevelAdjust attribute to a non-zero value, the CCAP may log an error upon execution of an XML configuration file that contains this attribute value.";
        }
        leaf modulation {
            type leafref {
                path "/ccap/docsis/modulation-profile/modulation-index";
            }
            mandatory true;
            description "A reference to a modulation index.";
        }
    }
    grouping ip-interface-group {
        leaf ip-interface-name {
            type string;
            description "Chassis unique name of the IP interface";
        }
        list primary-ipv4 {
            key ip-address;
            max-elements 1;
            ccap:inlineType;
            description "The primary-ipv4 list allow zero or one primary IPv4 address and prefix for this IP interface.";
            leaf ip-address {
                type ipv4-host-prefix;
                description "This attribute configures the primary IPv4 address and prefix for this instance.";
            }
            container yang-ext {
                ccap:extensionPoint; //different pyang flags impact use of this hint
                description "node for vendor YANG extensions";
            }
        }
        list ipv6 {
            key ipv6-address;
            description "The ipv6 list allows zero or more IPv6 interface addresses and prefixes to be configured for this IP interface";
            ccap:inlineType;
            leaf ipv6-address {
                type ipv6-host-prefix;
                description "This attribute configures the IPv6 address and prefix for this instance.";
            }
            container yang-ext {
                ccap:extensionPoint; //different pyang flags impact use of this hint
                description "node for vendor YANG extensions";
            }
        }
        list secondary-ipv4 {
            key ip-address;
            description "The secondary-ipv4 list allows zero or more secondary addresses and prefixes to be configured for this IP interface";
            ccap:inlineType;
            leaf ip-address {
                type ipv4-host-prefix;
                description "This attribute configures the secondary IPv4 address and prefix for this instance.";
            }
            container yang-ext {
                ccap:extensionPoint; //different pyang flags impact use of this hint
                description "node for vendor YANG extensions";
            }
        }
    }
    grouping enet-port-group
    {
        uses port-group;
        list ip-interface {
            key ip-interface-name;
            max-elements 1;
            ccap:inlineType;
            description "An ip-interface object.";
            uses ip-interface-group;
            leaf ingress-acl {
                type leafref {
                    path "/ccap/network/acl/acl-name";
                }
            }
            leaf egress-acl {
                type leafref {
                    path "/ccap/network/acl/acl-name";
                }
            }
            container yang-ext {
                ccap:extensionPoint; //different pyang flags impact use of this hint
                description "node for vendor YANG extensions";
            }
        }
    }
    grouping one-gb-ethernet-port-group
    {
        uses enet-port-group;
        leaf duplex {
  	        type duplex-type;
            default full-duplex;
            description "This attribute configures the Ethernet DuplexState of the interface.";
	    }
        leaf speed {
	    type ethernet-speed-type;
            mandatory true;
            description "This attribute configures the speed of the interface for interfaces that can support multiple speeds.";
        }
    }
    grouping epon-one-gb-port-reference {
        description "Reference to a onegigabit epon port.";
        leaf epon-slot {
            type leafref {
                path "/ccap/chassis/slot/slot-number";
            }
            description "Reference to the slot in which the onegigabit epon port resides.";
        }
        leaf epon-port-number {
            type leafref {
                path "/ccap/chassis/slot[slot-number=current()/../epon-slot]/one-gb-epon-port/port-number";
            }
            description "Reference to a onegigabit epon port number.";
        }
    }
    grouping epon-ten-gb-port-reference {
        description "Reference to a tengigabit epon port.";
        leaf epon-slot {
            type leafref {
                path "/ccap/chassis/slot/slot-number";
            }
            description "Reference to the slot in which the tengigabit epon port resides.";
        }
        leaf epon-port-number {
            type leafref {
                path "/ccap/chassis/slot[slot-number=current()/../epon-slot]/ten-gb-epon-port/port-number";
            }
            description "Reference to a tengigabit epon port number.";
        }
    }
    grouping udp-map {
        leaf udp-map-index {
            type uint32;
            description "This key represents a globally unique identifier of the UdpMap instance.";
        }
        leaf starting-udp-port {
            type inet:port-number;
            default 0;
            description "This attribute represents the UDP port range start value.";
        }
        leaf port-count {
            type uint32;
            default 0;
            description "This attribute represents the number of  UDP ports starting from 'StartingUdpPort' attribute value.";
        }
    }
    grouping authorizer-group {
        leaf auth-server-index {
            type uint32;
            description "The index is an unsigned, 32-bit identifier used as a key for this object instance.";
        }
        container auth-server {
            uses host;
            description "This attribute is the IP address/hostname of the RADIUS server referred to in this table entry.";
        }
        leaf auth-key {
            type string;
            mandatory true;
            description "This attribute corresponds to the shared secret that is used to encrypt the communication. Upon export, the CCAP MUST export the Key attribute of the object encrypted with a vendor-specific algorithm.";
        }
        leaf auth-clear-key {
            type boolean;
            mandatory true;
            description "This attribute indicates whether the Key attribute is included in the XML configuration file in the clear (true) or encrypted (false). This attribute defines the status of the key (encrypted or decrypted), not whether the device should export the key in the clear or encrypted. Regardless of the value of this setting, the key will always be exported as encrypted.";
        }
        leaf auth-timeout {
            type uint32 {
                range "1..4294967295";
            }
            units seconds;
            default 3;
            description "This attribute defines the number of seconds before a connection is declared inactive.";
        }
        leaf auth-retransmit-attempts {
            type uint32;
            units "Number of retransmissions";
            default 1;
            description "This attribute defines the number of retransmissions before giving up the connection.";
        }
        leaf primary-auth-server {
            type boolean;
            default false;
            description "This attribute designates whether this auth instance is the primary or backup server. If multiple instances are set to false, when the primary connection fails, the selection of which backup server to use is vendor specific.";
        }
        leaf source-ip-interface-name {
            type string;
            description "Local IP interface; must be a configured ip-interface name. If not specified, then the vendor picks the source IP address";
        }
    }
    grouping terminal-service-group {
        leaf screen-length {
            type uint16;
            default 24;
        }
        leaf screen-width {
            type uint16;
            default 80;
        }
        container input-transport-controls {
            leaf telnet-enabled {
                type boolean;
                default false;
            }
            leaf ssh-enabled {
                type boolean;
                default false;
            }
            container yang-ext {
                ccap:extensionPoint; //different pyang flags impact use of this hint
                description "node for vendor YANG extensions";
            }
        }
    }
    grouping ssm-group {
        leaf source-prefix-address {
            type inet:ip-prefix;
            mandatory true;
            description "This attribute identifies a specific Multicast Source prefix defined for this rule.
                         A source prefix of length 32 is a host source address.
                         A Source prefix of length zero is defined as 'all source addresses' (*, G).
                         Source prefix addresses are unicast addresses.";
            reference "RFC 3569 section 6; RFC 3306 sections 5 and 6.";
        }
        leaf group-prefix-address {
            type inet:ip-prefix;
            mandatory true;
            description "This attribute is the IP prefix corresponding to an IP multicast group.";
        }
    }
    grouping ecm-group {
        leaf ecm-index {
            type uint32;
            description "The Index is an unsigned, 32-bit identifier used as a key for this object.";
        }
        container ecm-server {
            uses host;
            description "This is the IP address/hostname of the ECM server.";
        }
        leaf ecm-server-port {
            type inet:port-number;
            mandatory true;
            description "This is the far-end TCP port for communicating with the ECM server.";
        }
        leaf ecm-cas-id {
            type ccap-octet-data-type {
               length "8";
            }
            mandatory true;
            description "This attribute defines the Ca System Id of the ECM server.";
        }
    }
    grouping video-session-group {
        leaf session-index {
            type uint32;
        }
        leaf session-name {
            type string;
            default " ";
            description "This attribute configures a name for the PID session. ";
        }
        leaf session-input-ts {
            mandatory true;
            type leafref {
                path "/ccap/video/video-input-ts/input-ts-index";
            }
            description "A reference to an input-ts-index.";
        }
        list session-output-ts {
          key session-output-ts-index;
          min-elements 1;
          description "A reference to an output-ts object.";
          leaf session-output-ts-index {
            type leafref {
              path "/ccap/video/video-output-ts/output-ts-index";
            }
            description "A reference to an output-ts-index.";
          }
          container yang-ext {
              ccap:extensionPoint; //different pyang flags impact use of this hint
              description "node for vendor YANG extensions";
          }
       }
    }
    grouping virtual-interface-group {
        leaf interface-index {
            type uint8;
            mandatory true;
            description "The index for this virtual ip-interface";
           }
        leaf admin-state {
            type admin-state-type;
            default down;
            description "This attribute configures the administrative state of the virtual interface.";
        }
        list ip-interface {
            key ip-interface-name;
            max-elements 1;
            ccap:inlineType;
            description "An ip-interface object.";
            uses ip-interface-group;
            container yang-ext {
                ccap:extensionPoint; //different pyang flags impact use of this hint
                description "node for vendor YANG extensions";
            }
        }
    }
    grouping view-config-ref {
        list view-config-ref {
            key view-name;
            leaf view-name {
                type leafref {
                    path "/ccap/management/snmp/view-config/view-name";
                }
            }
            min-elements 0;
            description "A reference to a view-configuration name.";
            container yang-ext {
                ccap:extensionPoint; //different pyang flags impact use of this hint
                description "node for vendor YANG extensions";
            }
        }
    }
    grouping acl-filter-group {
        choice protocol-type {
            case protocol-value {
                    ccap:inlineType;
	                leaf protocol-id {
	                    type uint8;
	                    mandatory true;
	                }
	                container yang-ext1 {
	                    ccap:extensionPoint; //different pyang flags impact use of this hint
	                    description "node for vendor YANG extensions";
	                }
            }
            case icmp {
                    ccap:inlineType;
	                leaf icmp-message-type {
	                    type uint16;
	                    mandatory true;
	                }
	                leaf icmp-message-code {
	                    type uint16;
	                }
	                container yang-ext2 {
	                    ccap:extensionPoint; //different pyang flags impact use of this hint
	                    description "node for vendor YANG extensions";
	                }
            }
            case igmp {
                container igmp {
                    ccap:inlineType;
	                leaf igmp-message-type {
	                    type uint16;
	                    mandatory true;
	                }
	                container yang-ext3 {
	                    ccap:extensionPoint; //different pyang flags impact use of this hint
	                    description "node for vendor YANG extensions";
	                }
                }
            }
            case yang-protocol-choice-ext {
                ccap:extensionPoint; //different pyang flags impact use of this hint
                description "node for vendor YANG extensions";
            }
        }
        leaf fragments {
            type boolean;
            default false;
        }
        choice source-port {
            case source-port-range {
                    ccap:inlineType;
	                leaf start-sport {
	                    type inet:port-number;
	                    mandatory true;
	                }
	                leaf end-sport {
	                    type inet:port-number;
	                    mandatory true;
	                }
	                container yang-ext7 {
	                    ccap:extensionPoint; //different pyang flags impact use of this hint
	                    description "node for vendor YANG extensions";
	                }
            }
            case single-source-port {
                    ccap:inlineType;
	                leaf sport {
	                    type inet:port-number;
	                    mandatory true;
	                }
	                leaf sport-comparator {
	                    type acl-comparator-type;
	                    default eq;
	                }
	                container yang-ext8 {
	                    ccap:extensionPoint; //different pyang flags impact use of this hint
	                    description "node for vendor YANG extensions";
	                }
            }
            case yang-sport-choice-ext {
                ccap:extensionPoint; //different pyang flags impact use of this hint
                description "node for vendor YANG extensions";
            }
        }
        choice dest-port {
            case dest-portrange {
                    ccap:inlineType;
	                leaf start-dport {
	                    type inet:port-number;
	                    mandatory true;
	                }
	                leaf end-dport {
	                    type inet:port-number;
	                    mandatory true;
	                }
	                container yang-ext9 {
	                    ccap:extensionPoint; //different pyang flags impact use of this hint
	                    description "node for vendor YANG extensions";
	                }
            }
            case single-dest-port {
                    ccap:inlineType;
	                leaf dport {
	                    type inet:port-number;
	                    mandatory true;
	                }
	                leaf dport-comparator {
	                    type acl-comparator-type;
	                    default eq;
	                }
	                container yang-ext10 {
	                    ccap:extensionPoint; //different pyang flags impact use of this hint
	                    description "node for vendor YANG extensions";
	                }
            }
            case yang-dport-choice-ext {
                ccap:extensionPoint; //different pyang flags impact use of this hint
                description "node for vendor YANG extensions";
            }
        }
    }
    grouping ofdma-ranging-group {
        leaf preamble-length {
            type uint16 {
                range "16..512";
            }
            units bit;
            default 128;
            description "This attribute defines the length of the OFDMA IUC preamble. For type 5 OFDMA channels, the burst descriptor type is 23 ([MULPI3.1], table 6.23), so this must be no greater than 512 bits ([MULPI3.1], table 6.25).";
        }
        leaf guard-band {
            type uint32;
            units hertz;
            mandatory true;
            description "This attribute is the sum of the upper and lower guard bands for initial ranging in Hz. This must correspond to an integral, even number of subcarriers.";
        }
    }
    grouping ccap-group {
        reference 
            "CCAP Operations Support System Interface Specification
             CM-SP-CCAP-OSSI-I01-110930 Ccap Object section.";
        leaf name {
            type string {
                length "1..32";
            }
            description "This attribute defines the name of the CCAP platform being configured.";
        }
        leaf description {
            type string;
            description "This attribute contains the description of the CCAP platform.";
        }
        leaf location {
            type string {
                length "1..128";
            }
            description "This attribute contains any location information for the CCAP.";
        }
        uses vendor-extension-version;
        container chassis {
            description "The Chassis container allows the user to configure the CCAP hardware elements.";
            list decryptor {
                key decryptor-index;
                description "The Decryptor object provides for the configuration of a Decryptor module or modules in the CCAP that are used to decrypt encrypted content delivered to the CCAP.  ";
                leaf decryptor-index {
                    type uint32;
                    description "The Index is an unsigned, 32-bit identifier used as a key for this object.";
                }
                leaf cw-timeout {
                    type uint32;
                    units seconds;
                    default 10;
                    description "This attribute configures the length of time in seconds that the decrypted should wait for an ECMD before switching to a redundant unit. ";
                }
                list ecmd-usage {
                    key ecmd-usage-index;
                    min-elements 1;
                    description "The ecmd-usage object provides for the configuration of multiple decryption sessions. It is an intermediate object that provides linkages between Decryptor objects and the ECMD(s) associated with those encrypted streams.";
                    leaf ecmd-usage-index {
                        type uint32;
                        description "This is an index for an instance of this object. The ecmd-usage object is a pointer to an ECMD that can be used for any program session that requires decryption as long as the CAS identifier of the input program matches.";
                    }
                    leaf priority {
                        type uint32;
                        mandatory true;
                        description "This is the configured selection priority for any program session that requires decryption when multiple ECMDs with the same CAS identifier are active. The ECMD with the lowest number should be selected first.";
                    }
                    leaf ecmd-ref {
                        type leafref {
                            path "/ccap/video/ecmd/ecm-index";
                        }
                        description "A reference to an instance of an ecmd object, referenced by its ecm-index.";
                    }
                    container yang-ext {
                        ccap:extensionPoint; //different pyang flags impact use of this hint
                        description "node for vendor YANG extensions";
                    }
                }
            }
            list fiber-node-config {
                key fiber-node-config-index;
                description 
                    "Fiber-node-config defines the cable hybrid fiber/coax system (HFC) plant Fiber Nodes reached by RF ports on a CCAP. 
                     This object supports the creation and deletion of multiple instances.";
                reference 
                    "DOCSIS 3.0 Operations Support System Interface Specification
                     CM-SP-OSSIv3.0-I15-110623 FiberNodeCfg Object section.";
                leaf fiber-node-config-index {
                    type uint32;
                    description "The index of the fiber node being configured.";
                }
                leaf fiber-node-name {
                    type string {
                        length "1..64";
                    }
                    mandatory true;
                    description "This key represents a human-readable name for a fiber node. ";
                    reference 
                        "DOCSIS 3.0 MAC and Upper Layer Protocols Interface Specification 
                         CM-SP-MULPIv3.0-I16-110623 RF Topology Configuration section.";
                }
                leaf description {
                    type string;
                    default " ";
                    description "This attribute represents a human-readable description of the node.";
                }
                list ds-rf-port-ref {
                    key "slot ds-rf-port";
                    description "This object associates a downstream RF port with this fiber node configuration instance.";
                    uses ds-rf-port-reference;
                    container yang-ext {
                        ccap:extensionPoint; //different pyang flags impact use of this hint
                        description "node for vendor YANG extensions";
                    }
                }
                list us-rf-port-ref {
                    key "slot us-rf-port";
                    description "This object associates an upstream RF port with this fiber node configuration instance.";
                    uses us-rf-port-reference;
                    container yang-ext {
                        ccap:extensionPoint; //different pyang flags impact use of this hint
                        description "node for vendor YANG extensions";
                    }
                }
                container yang-ext {
                    ccap:extensionPoint; //different pyang flags impact use of this hint
                    description "node for vendor YANG extensions";
                }
            }
            list slot {
                key slot-number;
                description "This object configures a slot within the CCAP chassis. Line cards reside in slots.";
                reference 
                    "CCAP Operations Support System Interface Specification
                     CM-SP-CCAP-OSSI-I01-110930 Slot section.";
                leaf slot-number {
                    type uint8;
                    description "This attribute configures the slot number for which a LineCard object will be configured. The Number attribute is a zero- or one-based index that sequentially numbers the physical slots in the chassis. For example, the Slot numbers start at zero and increase to n-1, where n is the number of slots the chassis supports.";
                }
                choice line-card-type {
                    mandatory true;
                    case rf-line-card {
                            description "This is an RF line card that can have downstream RF ports, upstream RF ports, or both.";
                            reference 
                                "CCAP Operations Support System Interface Specification
                                 CM-SP-CCAP-OSSI-I01-110930 UsDsRfLineCard section.";
                            container rf-card {
                                uses line-card-group;
                            }
                            list encryptor {
                                key encryptor-index;
                                description 
                                    "This object allows for the configuration of an Encryptor. Each Encryptor
                                     object is part of a DLC. Each is associated with at
                                     least one active and zero or more backup ECMGs. For
                                     Simulcrypt, the Encryptor would be associated with
                                     multiple active ECMGs, each for a different
                                     CAS. Each is also associated with one or more video
                                     sessions that is being encrypted on this DLC.";
                                uses encryptor-group;
                                container yang-ext {
                                    ccap:extensionPoint; //different pyang flags impact use of this hint
                                    description "node for vendor YANG extensions";
                                }
                            }
                            leaf enable-udp-map-encryption {
                                type leafref {
                                    path "/ccap/video/static-udp-map-encryption/udp-map-encryption-index";
                                }
                                description "Reference to an encryptor for all statically udp port mapped sessions on this card.
                                             If not present, no statically udp port mapped video session is encrypted locally.";
                            }
                            list us-rf-port {
                                key port-number;
                                description 
                                    "A us-rf-port object represents a physical upstream RF connector on a CCAP
                                     line card.  It is derived from the Port abstract
                                     class, and so inherits all attributes of that
                                     class, including its associations.  A UsRfPort may
                                     be contained by either a UsRfLineCard or a
                                     UsDsRfLineCard. It contains one or more
                                     upstream-physical-channels. This object has no
                                     attributes other than what has been inherited from
                                     the abstract class Port, but does have several
                                     associations.";
                                uses us-rf-port-group;
                                container yang-ext {
                                    ccap:extensionPoint; //different pyang flags impact use of this hint
                                    description "node for vendor YANG extensions";
                                }
                            }
                            list ds-rf-port {
                                key port-number;
                                description 
                                    "This object allows for the configuration of a physical Downstream RF
                                     port on a DLC or UsDsRfLineCard.  The DsRfPort is a
                                     type of the abstract class Port and inherits those
                                     common parameters.  In the CCAP, a single port now
                                     encompasses the entire downstream spectrum instead
                                     of a few carriers as are seen in the current
                                     generation EQAM and CMTS products.";
                                uses ds-rf-port-group;
                                container yang-ext {
                                    ccap:extensionPoint; //different pyang flags impact use of this hint
                                    description "node for vendor YANG extensions";
                                }
                            }
                            container yang-ext1 {
                                ccap:extensionPoint; //different pyang flags impact use of this hint
                                description "node for vendor YANG extensions";
                            }
                    }
                    case epon-line-card {
                            description "This object configures an EPON line card. An epon-line-card that only supports PON Ports of type one-gb-epon-port must not have a configured enet-port. An epon-line-card that supports PON ports of type ten-gb-epon-port may have a configured enet-port.";
                            container epon-card {
                                uses line-card-group;
                            }
                            list one-gb-epon-port {
                                key port-number;
                                description "This configuration object allows for a one Gigabit EPON port to be configured on an EPON line card. It is a type of the abstract class PonPort.";
                                uses port-group;
                                leaf upstream-fec-mode {
                                    type upstream-fec-mode-type;
                                    default disabled;
                                    description 
                                         "This attribute configures the FEC mode applied to the EPON upstream. The perOnu option allows the ONU provisioning process to determine whether FEC should be enabled or disabled. This option is only valid for 1G EPON interfaces.
                                         The default value for the 1G EPON interface would be 'disabled'.
                                         The default value for the 10G EPON interface would be 'enabled'.
                                         The value of other(1) is used when a vendor-extension has been implemented for this attribute.";
                                }
                                leaf downstream-fec-mode {
                                    type downstream-fec-mode-type;
                                    default disabled;
                                    description 
                                        "This attribute configures the FEC mode of the EPON downstream. The perOnu option allows the ONU provisioning process to determine whether FEC should be enabled or disabled. This option is only valid for 1G EPON interfaces.
                                         The default value for the 1G EPON interface would be 'disabled'.
                                         The default value for the 10G EPON interface would be 'enabled'.
                                         The value of other(1) is used when a vendor-extension has been implemented for this attribute.";
                                }
                                container yang-ext {
                                    ccap:extensionPoint; //different pyang flags impact use of this hint
                                    description "node for vendor YANG extensions";
                                }
                            }
                            list ten-gb-epon-port {
                                key port-number;
                                description "This configuration object allows for a symmetric or asymmetric ten Gigabit EPON port to be configured on an EPON line card. It is a type of the abstract class PonPort";
                                leaf pon-type {
				                    type pon-symmetry-type;
                                    mandatory true;
                                    description "This attribute configures the speed of the 10G EPON interfaces on the line card and allows for asymmetrical upstream and downstream speeds.";
                                }
                                uses port-group;
                                leaf upstream-fec-mode {
                                    type upstream-fec-mode-type;
                                    default enabled;
                                    description 
                                         "This attribute configures the FEC mode applied to the EPON upstream. The perOnu option allows the ONU provisioning process to determine whether FEC should be enabled or disabled. This option is only valid for 1G EPON interfaces.
                                         The default value for the 1G EPON interface would be 'disabled'.
                                         The default value for the 10G EPON interface would be 'enabled'.
                                         The value of other(1) is used when a vendor-extension has been implemented for this attribute.";
                                }
                                leaf downstream-fec-mode {
                                    type downstream-fec-mode-type;
                                    default enabled;
                                    description 
                                        "This attribute configures the FEC mode of the EPON downstream. The perOnu option allows the ONU provisioning process to determine whether FEC should be enabled or disabled. This option is only valid for 1G EPON interfaces.
                                         The default value for the 1G EPON interface would be 'disabled'.
                                         The default value for the 10G EPON interface would be 'enabled'.
                                         The value of other(1) is used when a vendor-extension has been implemented for this attribute.";
                                }
                                container yang-ext {
                                    ccap:extensionPoint; //different pyang flags impact use of this hint
                                    description "node for vendor YANG extensions";
                                }
                            }
                            list one-gb-ethernet-epon-port {
                                key port-number;
                                description "This object configures a one gigabit interface for an Ethernet port. The speed and duplex settings for this type of port can be configured via this object.";
                                uses one-gb-ethernet-port-group;
                                container yang-ext {
                                    ccap:extensionPoint; //different pyang flags impact use of this hint
                                    description "node for vendor YANG extensions";
                                }
                            }
                            list ten-gb-ethernet-epon-port {
                                key port-number;
                                description "This object configures a ten gigabit interface for an Ethernet port.";
                                uses enet-port-group;
                                container yang-ext {
                                    ccap:extensionPoint; //different pyang flags impact use of this hint
                                    description "node for vendor YANG extensions";
                                }
                            }
                            list forty-gb-ethernet-epon-port {
                                key port-number;
                                description "This object configures a 40 gigabit interface for an Ethernet port.";
                                uses enet-port-group;
                                container yang-ext {
                                    ccap:extensionPoint; //different pyang flags impact use of this hint
                                    description "node for vendor YANG extensions";
                                }
                            }
                            list one-hundred-gb-ethernet-epon-port {
                                key port-number;
                                description "This object configures a 100 gigabit interface for an Ethernet port.";
                                uses enet-port-group;
                                container yang-ext {
                                    ccap:extensionPoint; //different pyang flags impact use of this hint
                                    description "node for vendor YANG extensions";
                                }
                            }
                            container yang-ext2 {
                                ccap:extensionPoint; //different pyang flags impact use of this hint
                                description "node for vendor YANG extensions";
                            }
                    }
                    case sre-line-card {
                            description "The sre-line-card is the name given to the line card in the integrated CCAP chassis that contains all the NSI and Management functions for the CCAP. This line card is associated with EnetPort. This object inherits a number of attributes from the LineCard abstract object.";
                            container sre-card {
                                uses line-card-group;
                            }
                            list one-gb-ethernet-port {
                                key port-number;
                                description "This object configures a one gigabit interface for an Ethernet port. The speed and duplex settings for this type of port can be configured via this object.";
                                uses one-gb-ethernet-port-group;
                                container yang-ext {
                                    ccap:extensionPoint; //different pyang flags impact use of this hint
                                    description "node for vendor YANG extensions";
                                }
                            }
                            list ten-gb-ethernet-port {
                                key port-number;
                                description "This object configures a ten gigabit interface for an Ethernet port.";
                                uses enet-port-group;
                                container yang-ext {
                                    ccap:extensionPoint; //different pyang flags impact use of this hint
                                    description "node for vendor YANG extensions";
                                }
                            }
                            list forty-gb-ethernet-port {
                                key port-number;
                                description "This object configures a 40 gigabit interface for an Ethernet port.";
                                uses enet-port-group;
                                container yang-ext {
                                    ccap:extensionPoint; //different pyang flags impact use of this hint
                                    description "node for vendor YANG extensions";
                                }
                            }
                            list one-hundred-gb-ethernet-port {
                                key port-number;
                                description "This object configures a 100 gigabit interface for an Ethernet port.";
                                uses enet-port-group;
                                container yang-ext {
                                    ccap:extensionPoint; //different pyang flags impact use of this hint
                                    description "node for vendor YANG extensions";
                                }
                            }
                            container yang-ext3 {
                                ccap:extensionPoint; //different pyang flags impact use of this hint
                                description "node for vendor YANG extensions";
                            }
                    }
                    case yang-choice-ext {
                        ccap:extensionPoint; //different pyang flags impact use of this hint
                        description "node for vendor YANG extensions";
                    }
                }
                container yang-ext {
                    ccap:extensionPoint; //different pyang flags impact use of this hint
                    description "node for vendor YANG extensions";
                }
            }
            list video-phy-profile {
                key phy-index;
                description "The video-phy-profile list is a specialization of the down-channel-phy-params object. It specifies values for video PHY parameters when those parameters are not set at the channel level. At least one entry must always be present and not be deletable. The index of such entries is vendor specific. While one element must be defined for each vendor's list, it is not required that this element be configured (i.e., it could be defaulted), so min-elements is zero, not one";
                reference 
                    "CCAP Operations Support System Interface Specification
                     CM-SP-CCAP-OSSI-I01-110930 DrfCfg section.";
                uses down-channel-phy-params-group;
                leaf spectrum-inversion {
                    type boolean;
                    default false;
                    description "This attribute specifies global default RF Signal Spectrum inversion. When set to 'true', it indicates that the QAM channel spectrum is inverted.";
                }
                leaf symbol-rate-override {
                    type uint32;
                    description "Sets the symbol rate for the video channel. Video channels can have more than one symbol rate for a single modulation, unlike DOCSIS channels. If not specified, channels configured to use this profile operate with the value specified by DOCSIS for the Annex and modulation.";
                }
                container yang-ext {
                    ccap:extensionPoint; //different pyang flags impact use of this hint
                    description "node for vendor YANG extensions";
                }
            }
            list docsis-phy-profile {
                key phy-index;
                description "The docsis-phy-profile list is a specialization of the down-channel-phy-params object. It specifies values for video PHY parameters when those parameters are not set at the channel level. At least one entry must always be present and not be deletable. The index of such entries is vendor specific. While one element must be defined for each vendor's list, it is not required that this element be configured (i.e., it could be defaulted), so min-elements is zero, not one";
                reference 
                    "CCAP Operations Support System Interface Specification
                     CM-SP-CCAP-OSSI-I01-110930 DrfCfg section.";
                uses down-channel-phy-params-group;
            }
            container yang-ext {
                ccap:extensionPoint; //different pyang flags impact use of this hint
                description "node for vendor YANG extensions";
            }
        }
        container docsis {
            description "The docsis object is the primary container of DOCSIS configuration objects.";
            reference 
                "CCAP Operations Support System Interface Specification
                 CM-SP-CCAP-OSSI-I01-110930 DOCSIS Configuration Objects section.";
            choice global-params {
	            case docs-global {
	                description "The docs-global object is the container for the DOCSIS global configuration objects.";
	                leaf maximum-scheduled-codes-enabled {
	                    type boolean;
	                    mandatory true;
	                    description "Indicates the global state of the Maximum Scheduled Code feature on the CCAP. The value true indicates that this feature can be enabled on individual logical channels on the CCAP. The value false indicates that the feature is not in operations on the CCAP. Note that the CCAP Object attribute ScdmaChannelMscState enables or disables Maximum Scheduled Codes on a per logical channel basis.
	";
	                }
	                leaf l2-vpn-global-enabled {
	                    type boolean;
	                    default false;
	                    description "This attribute will enable or disable on a global basis the configuration of L2VPN forwarding for all DOCSIS MAC Domains. The default value is false. This attribute only enables L2VPN forwarding; configuration of the feature is handled in a vendor-specific way.";
	                }
	                container yang-ext1 {
	                    ccap:extensionPoint; //different pyang flags impact use of this hint
	                    description "node for vendor YANG extensions";
	                }
	            }
            }
            list cm-vendor-oui {
                key cm-oui;
                min-elements 0;
                description "Cm-vendor-oui allows the operator to create a database of OUIs and Vendors.";
                leaf cm-oui {
                    type ccap-octet-data-type {
                        length "6";
                    }
                    description "This attribute configures the OUI portion of a given MAC address.";
                }
                leaf cm-vendor-name {
                    type string;
                    mandatory true;
                    description "This attribute configures the company name of the vendor with the associated OUI.";
                }
                container yang-ext {
                    ccap:extensionPoint; //different pyang flags impact use of this hint
                    description "node for vendor YANG extensions";
                }
            }
            container docs-security {
                description "The docs-security container is the primary container of DOCSIS security configuration objects.";
                list sav-config-list {
                    key "sav-config-list-name";
                    min-elements 0;
                    description 
                        "A sav-config-list node consists of read-write objects and is based on the docsSecSavCfgListEntry defined in [OSSIv3.0] and will be used with no modifications for CCAP. The RowStatus attribute has been removed.
                         This object supports the creation and deletion of multiple instances. Each object instance defines one CMTS configured subnet prefix extension for which the CCAP performs source address verification. 
                         Creation of a new instance of this object requires the PrefixAddrType and PrefixAddr attributes to be set.";
                    reference 
                        "DOCSIS 3.0 Operations Support System Interface Specification
                         CM-SP-OSSIv3.0-I15-110623 DOCS-SEC-MIB section.";
                    leaf sav-config-list-name {
                        type string;
                        description "This attribute is the key that identifies the instance of the SavCmAuth object to which this object extension belongs.";
                    }
                    list sav-rule {
                        key "rule-id";
	                min-elements 1;
	                description "The rules for a particular sav-config-list.";
	                leaf rule-id {
	                    type uint32;
	                    description "This attribute is the key that identifies a particular subnet prefix rule of an instance of this object.";
	                }
	                leaf prefix-address {
	                    type inet:ip-prefix;
	                    mandatory true;
	                    description "This attribute corresponds to the IP address and prefix of this subnet prefix rule.";
	                }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                container cmts-sav-control {
                    description "Cmts-sav-control container defines attributes for global Source Address Verification (SAV) configuration. 
";
                    reference 
                        "DOCSIS 3.0 Operations Support System Interface Specification
                         CM-SP-OSSIv3.0-I15-110623 DOCS-SEC-MIB section.";
                    leaf cm-authentication-enable {
                        type boolean;
                        default true;
                        description 
                            "This attribute enables or disables Source Address Verification (SAV) for CM configured policies in the SavCmAuth object. If this attribute is set to 'false', the CM configured policies in the SavCmAuth object are ignored.
                             This attribute is only applicable when the SrcAddrVerificationEnabled attribute of the MdCfg object is 'true'.";
                    }
                    container yang-ext {
                        ccap:extensionPoint; //different pyang flags impact use of this hint
                        description "node for vendor YANG extensions";
                    }
                }
                choice server {
	                case cmts-server-config {
	                    description "Cmts-server-config container defines attributes for configuring TFTP Configuration File Security features. 
	";
	                    reference 
	                        "DOCSIS 3.0 Operations Support System Interface Specification
	                         CM-SP-OSSIv3.0-I15-110623 DOCS-SEC-MIB section.";
	                    leaf tftp-options {
	                        type bits {
	                            bit hw-addr {
	                                position 0;
	                            }
	                            bit net-addr {
	                                position 1;
	                            }
	                        }
	                        mandatory true;
	                        description 
	                            "This attribute instructs the CMTS to insert the source IP address and/or MAC address of received TFTP packets into the TFTP option fields before forwarding the packets to the Config File server. 
	                             This attribute is only applicable when the TftpProxyEnabled attribute of the MdCfg object is 'true'.";
	                    }
	                    leaf config-file-learning-enabled {
	                        type boolean;
	                        default true;
	                        description 
	                            "This attribute enables and disables Configuration File Learning functionality. 
	                             If this attribute is set to 'true' the CMTS will respond with Authentication Failure in the REG-RSP message when there is a mismatch between learned config file parameters and REG-REQ parameters. If this attribute is set to 'false', the CMTS will not execute config file learning and mismatch check. 
	                             This attribute is only applicable when the TftpProxyEnabled attribute of the MdCfg object is 'true'.";
	                    }
	                    container yang-ext2 {
	                        ccap:extensionPoint; //different pyang flags impact use of this hint
	                        description "node for vendor YANG extensions";
	                    }
	                }
                }
                container cmts-encrypt {
                    description "Cmts-encrypt container includes an attribute which defines the order in which encryption algorithms are to be applied.
";
                    reference 
                        "DOCSIS 3.0 Operations Support System Interface Specification
                         CM-SP-OSSIv3.0-I15-110623 DOCS-SEC-MIB section.";
                    leaf encrypt-alg-priority {
                        type snmp-tag-list-type;
                        default "aes128CbcMode des56CbcMode des40CbcMode";
                        description 
                            "This attribute allows for configuration of a prioritized list of encryption algorithms the CMTS will use when selecting the primary SAID encryption algorithm for a given CM. The CMTS selects the highest priority encryption algorithm from this list that the CM supports. By default the following encryption algorithms are listed from highest to lowest priority (left being the highest): 128 bit AES, 56 bit DES, 40 bit DES.
                             An empty list indicates that the CMTS attempts to use the latest and most robust encryption algorithm supported by the CM. The CMTS will ignore unknown values or unsupported algorithms.";
                    }
                    container yang-ext {
                        ccap:extensionPoint; //different pyang flags impact use of this hint
                        description "node for vendor YANG extensions";
                    }
                }
                container cmts-certificate {
                    description "Cmts-certificate container defines attributes for global certificate revocation configuration.";
                    reference 
                        "DOCSIS 3.0 Operations Support System Interface Specification
                         CM-SP-OSSIv3.0-I15-110623 DOCS-SEC-MIB section.";
                    leaf cert-revocation-method {
		                type cert-revocation-method-type;
                        default none;
                        description 
                            "This attribute identifies which certificate revocation method is to be used by the CMTS to verify the cable modem certificate validity.";
                    }
                    container yang-ext {
                        ccap:extensionPoint; //different pyang flags impact use of this hint
                        description "node for vendor YANG extensions";
                    }
                }
                list cmts-cert-revocation-list {
                    key url;
                    description 
                        "Cmts-cert-revocation-list consists of the read-write objects under the CmtsCertRevocationList object identifier defined in [OSSIv3.0]. The LastUpdate attribute has been removed.
                         This object defines a CRL location URL and periodic refresh interval value. The CRL location URL defines from where the CCAP will retrieve the CRL file. The periodic refresh interval value indicates how often the CCAP will retrieve the CRL file for updates if the tbsCertList.nextUpdate attribute in the file is absent. 
                         This object is only applicable when the CertRevocationMethod attribute of the DocsSecCmtsCertificate object is set to 'crl' or 'crlAndOcsp'.";
                    reference 
                        "DOCSIS 3.0 Operations Support System Interface Specification
                         CM-SP-OSSIv3.0-I15-110623 DOCS-SEC-MIB section.";
                    leaf url {
                        type string;
                        mandatory true;
                        description "This attribute contains the URL from where the CMTS will retrieve the CRL file. When this attribute is set to a URL value different from the current value, it triggers the CMTS to retrieve the CRL file from that URL. If the value of this attribute is a zero-length string, the CMTS does not attempt to retrieve the CRL.
";
                        reference 
                            "DOCSIS 3.0 Security Specification CM-SP-SECv3.0-I13-100611,
                             BPI+ X.509 Certificate Profile and Management section.";
                    }
                    leaf refresh-interval {
                        type uint32 {
                            range "1..524160";
                        }
                        units minutes;
                        default 10080;
                        description "This attribute contains the refresh interval for the CMTS to retrieve the CRL (referred to in the Url attribute) with the purpose of updating its Certificate Revocation List. This attribute is meaningful if the tbsCertList.nextUpdate attribute does not exist in the last retrieved CRL, otherwise the value 0 is returned.
";
                        reference 
                            "DOCSIS 3.0 Security Specification CM-SP-SECv3.0-I13-100611,
                             BPI+ X.509 Certificate Profile and Management section.";
                    }
                    container yang-ext {
                        ccap:extensionPoint; //different pyang flags impact use of this hint
                        description "node for vendor YANG extensions";
                    }
                }
                list cmts-cm-eae-exclusion {
                    key cmts-cm-eae-exclusion-id;
                    description 
                        "This configuration object consists of the read-write objects of the docsSecCmtsCmEaeExclusion object is defined in [OSSIv3.0] and will be used with no further modifications for CCAP. The RowStatus attribute has been removed.
                         This object defines a list of CMs or CM groups to exclude from Early Authentication and Encryption (EAE). This object allows overrides to the value of EAE Control for individual CMs or group of CMs for purposes such as debugging. 
                         The CCAP MUST support a minimum of 30 instances of the CmtsCmEaeExclusion object. 
                         This object is only applicable when the EarlyAuthEncryptCtrl attribute of the MdCfg object is enabled.
                         This object supports the creation and deletion of multiple instances.";
                    reference 
                        "DOCSIS 3.0 Operations Support System Interface Specification
                         CM-SP-OSSIv3.0-I15-110623 DOCS-SEC-MIB section.";
                    leaf cmts-cm-eae-exclusion-id {
                        type uint32 {
                            range "1..4294967295";
                        }
                        description "This key uniquely identifies the exclusion MAC address rule.";
                    }
                    leaf mac-address {
                        type yang:mac-address;
                        default 00:00:00:00:00:00;
                        description "This attribute identifies the CM MAC address. A match is made when a CM MAC address bitwise ANDed with the MacAddrMask attribute equals the value of this attribute.";
                    }
                    leaf mac-address-mask {
                        type yang:mac-address;
                        default FF:FF:FF:FF:FF:FF;
                        description "This attribute identifies the CM MAC address mask and is used with the MacAddr attribute.";
                    }
                    container yang-ext5 {
                        ccap:extensionPoint; //different pyang flags impact use of this hint
                        description "node for vendor YANG extensions";
                    }
                }
                list cmts-online-cert-status-protocol {
                    key url;
                    max-elements 1;
                    description 
                        "This configuration object is defined in [OSSIv3.0] and will be used with no modifications for CCAP.
                         This object contains an OCSP Responder URL and an attribute to bypass signature checking of the OCSP response, as detailed in [RFC 2560]. The CCAP will use the URL for OCSP communications in checking a certificate's revocation status. This object is only applicable when the CertRevocationMethod attribute of the CmtsCertificate object is set to 'ocsp' or 'crlAndOcsp'.";
                    reference 
                        "DOCSIS 3.0 Operations Support System Interface Specification
                         CM-SP-OSSIv3.0-I15-110623 DOCS-SEC-MIB section.";
                    leaf url {
                        type string;
                        mandatory true;
                        description "This attribute contains the URL string to retrieve OCSP information. If the value of this attribute is a zero-length string, the CMTS does not attempt to request the status of a CM certificate.
";
                        reference 
                            "DOCSIS 3.0 Security Specification CM-SP-SECv3.0-I13-100611,
                             BPI+ X.509 Certificate Profile and Management section; RFC 2560.";
                    }
                    leaf signature-bypass {
                        type boolean;
                        default false;
                        description "This attribute enables or disables signature checking on OCSP response messages. ";
                        reference 
                            "DOCSIS 3.0 Security Specification CM-SP-SECv3.0-I13-100611,
                             BPI+ X.509 Certificate Profile and Management section; RFC 2560.";
                    }
                    container yang-ext {
                        ccap:extensionPoint; //different pyang flags impact use of this hint
                        description "node for vendor YANG extensions";
                    }
                }
                choice sys-bpi {
	                case sys-bpi-config {
	                    description "This object provides the configuration of the system-wide default Baseline Privacy key lifetimes. If not configured, the default values are vendor specific.";
	                    reference "RFC 3083";
	                    leaf sys-default-authentication-lifetime {
	                        type uint32;
	                        units seconds;
	                        mandatory true;
	                        description "The value of this object is the default lifetime, in seconds, the CCAP assigns to a new authorization key.";
	                    }
	                    leaf sys-default-tek-lifetime {
	                        type uint32;
	                        units seconds;
	                        mandatory true;
	                        description "The value of this object is the default lifetime, in seconds, the CCAP assigns to a new Traffic Encryption Key (TEK).";
	                    }
	                    container yang-ext3 {
	                        ccap:extensionPoint; //different pyang flags impact use of this hint
	                        description "node for vendor YANG extensions";
	                    }
	                }
                }
                container yang-ext {
                    ccap:extensionPoint; //different pyang flags impact use of this hint
                    description "node for vendor YANG extensions";
                }
            }
            container docs-subscriber-management {
                description "This group of configuration elements allows for the configuration of the Subscriber Management rules. They are based on the configuration elements from [OSSIv3.0]";
                container base {
                    description "This object defines the configuration parameters of Subscriber Management features for the CM in case the CM does not signal any of the parameters during the registration process.

";
                    reference 
                        "DOCSIS 3.0 Operations Support System Interface Specification
                         CM-SP-OSSIv3.0-I15-110623 Base Object section.";
                    leaf cpe-max-ipv4 {
                        type uint16 {
                            range "0..1023";
                        }
                        default 16;
                        description "This attribute represents the maximum number of IPv4 addresses allowed for the CM's CPE if not signaled in the registration process.";
                    }
                    leaf cpe-max-ipv6 {
                        type uint16 {
                            range "0..1023";
                        }
                        default 16;
                        description "This attribute represents the maximum number of IPv6 Prefixes and addresses allowed for the CM's CPEs if not signaled in the registration process. All IPv6 prefixes and addresses, including Link-Local and any address with a scope greater than 1 are counted against the CpeMax Ipv6AddressesDef.";
                    }
                    leaf cpe-active {
                        type boolean;
                        default false;
                        description "This attribute represents the default value for enabling Subscriber Management filters and controls in the CM if the parameter is not signaled in the DOCSIS Registration process.";
                    }
                    leaf cpe-learnable {
                        type boolean;
                        default true;
                        description "This attribute represents the default value for enabling the CPE learning process for the CM if the parameter is not signaled in the DOCSIS Registration process.";
                    }
                    leaf subscriber-downstream-filter {
                        type uint16 {
                            range "0..1024";
                        }
                        default 0;
                        description "This attribute represents the default value for the subscriber (CPE) downstream filter group for the CM if the parameter is not signaled in the DOCSIS Registration process.";
                    }
                    leaf subscriber-upstream-filter {
                        type uint16 {
                            range "0..1024";
                        }
                        default 0;
                        description "This attribute represents the default value for the subscriber (CPE) upstream filter group for the CM if the parameter is not signaled in the DOCSIS Registration process.";
                    }
                    leaf cm-downstream-filter {
                        type uint16 {
                            range "0..1024";
                        }
                        default 0;
                        description "This attribute represents the default value for the CM stack downstream filter group applying to the CM if the parameter is not signaled in the DOCSIS Registration process.";
                    }
                    leaf cm-upstream-filter {
                        type uint16 {
                            range "0..1024";
                        }
                        default 0;
                        description "This attribute represents the default value for the CM stack upstream filter group for the CM if the parameter is not signaled in the DOCSIS Registration process.";
                    }
                    leaf ps-downstream-filter {
                        type uint16 {
                            range "0..1024";
                        }
                        default 0;
                        description "This attribute represents the default value for the PS or eRouter downstream filter group for the CM if the parameter is not signaled in the DOCSIS Registration process.";
                    }
                    leaf ps-upstream-filter {
                        type uint16 {
                            range "0..1024";
                        }
                        default 0;
                        description "This attribute represents the default value for the PS or eRouter upstream filter group for the CM if the parameter is not signaled in the DOCSIS Registration process.";
                    }
                    leaf mta-downstream-filter {
                        type uint16 {
                            range "0..1024";
                        }
                        default 0;
                        description "This attribute represents the default value for the MTA downstream filter group for the CM if the parameter is not signaled in the DOCSIS Registration process.";
                    }
                    leaf mta-upstream-filter {
                        type uint16 {
                            range "0..1024";
                        }
                        default 0;
                        description "This attribute represents the default value for the MTA upstream filter group for the CM if the parameter is not signaled in the DOCSIS Registration process.";
                    }
                    leaf stb-downstream-filter {
                        type uint16 {
                            range "0..1024";
                        }
                        default 0;
                        description "This attribute represents the default value for the STB downstream filter group for the CM if the parameter is not signaled in the DOCSIS Registration process.";
                    }
                    leaf stb-upstream-filter {
                        type uint16 {
                            range "0..1024";
                        }
                        default 0;
                        description "This attribute represents the default value for the STB upstream filter group for the CM if the parameter is not signaled in the DOCSIS Registration process.";
                    }
                    container yang-ext {
                        ccap:extensionPoint; //different pyang flags impact use of this hint
                        description "node for vendor YANG extensions";
                    }
                }
                list filter-group {
                    key "rule-id group-id";
                    min-elements 0;
                    description 
                        "This object describes a set of filter or classifier criteria. Classifiers are assigned by group to the individual CMs. That assignment is made via the Subscriber Management TLVs encodings sent upstream from the CM to the CMPA during registration, or in their absence, default values configured in the CCAP.
                         A Filter Group ID (GrpId) is a set of rules that correspond to the expansion of a UDC Group ID into individual UDC rules. The UDC Group IDs are linked to Ids of the FilterGrp object so the CCAP can signal those filter rules as UDCs to the CM during the registration process. Implementation of L2 classification criteria is optional for the CCAP; LLC/MAC upstream and downstream filter criteria can be ignored during the packet matching process.";
                    reference 
                        "DOCSIS 3.0 Operations Support System Interface Specification
                         CM-SP-OSSIv3.0-I15-110623 FilterGrp Object section.";
                    leaf group-id {
                        type uint16 {
                            range "1..1024";
                        }
                        mandatory true;
                        description "This key is an identifier for a set of classifiers known as a filter group. Each CM may be associated with several filter groups for its upstream and downstream traffic, one group per target end point on the CM as defined in the Grp object. Typically, many CMs share a common set of filter groups. The range for this attribute is 1 to 1024 to align it with the values used in the Base Object.";
                    }
                    leaf rule-id {
                        type uint16 {
                            range "1..65535";
                        }
                        mandatory true;
                        description "This key represents an ordered classifier identifier within the group. Filters are applied in order if the Priority attribute is not supported.";
                    }
                    leaf filter-action {
		      type filter-action-type;
                        default permit;
                        description "This attribute represents the action to take upon this filter matching.";
                    }
                    leaf priority {
                        type uint16;
                        default 0;
                        description "This attribute defines the order in which the classifiers are compared against packets. The higher the value, the higher the priority.";
                    }
                    leaf ip-tos-low {
                        type ccap-octet-data-type {
                            length "2";
                        }
                        default 00;
                        description "This attribute represents the low value of a range of ToS (Type of Service) octet values. The IP ToS octet, as originally defined in [RFC 791], has been superseded by the 6-bit Differentiated Services Field (DSField, [RFC 3260]) and the 2-bit Explicit Congestion Notification Field (ECN field, [RFC 3168]). This attribute is defined as an 8-bit octet as per the DOCSIS Specification for packet classification.
";
                        reference 
                            "DOCSIS 3.0 MAC and Upper Layer Protocols Interface Specification 
                             CM-SP-MULPIv3.0-I16-110623; RFC 791; RFC 3168; RFC 3260.";
                    }
                    leaf ip-tos-high {
                        type ccap-octet-data-type {
                            length "2";
                        }
                        default 00;
                        description "This attribute represents the high value of a range of ToS octet values. The IP ToS octet, as originally defined in [RFC 791], has been superseded by the 6-bit Differentiated Services Field (DSField, [RFC 3260]) and the 2-bit Explicit Congestion Notification Field (ECN field, [RFC 3168]). This attribute is defined as an 8-bit octet as per the DOCSIS Specification for packet classification.
";
                        reference 
                            "DOCSIS 3.0 MAC and Upper Layer Protocols Interface Specification 
                             CM-SP-MULPIv3.0-I16-110623; RFC 791; RFC 3168; RFC 3260.";
                    }
                    leaf ip-tos-mask {
                        type ccap-octet-data-type {
                            length "2";
                        }
                        default 00;
                        description "This attribute represents the mask value that is bitwise ANDed with ToS octet in an IP packet, and the resulting value is used for range checking of IpTosLow and IpTosHigh.";
                    }
                    leaf ip-protocol {
                        type uint16 {
                            range "0..257";
                        }
                        default 256;
                        description "This attribute represents the value of the IP Protocol field required for IP packets to match this rule. The value 256 matches traffic with any IP Protocol value. The value 257 by convention matches both TCP and UDP.";
                    }
                    leaf source-address {
                        type inet:ip-prefix;
                        mandatory true;
                        description "This attribute specifies the value of the IP Source Address required for packets to match this rule and which bits of a packet's IP Source Address are compared to match this rule. An IP packet matches the rule when the packet's IP Source Address bitwise ANDed with the mask value defined by the prefix equals the InetSrcAddr value. ";
                    }
                    leaf destination-address {
                        type inet:ip-prefix;
                        mandatory true;
                        description "This attribute specifies the value of the IP Destination Address required for packets to match this rule and which bits of a packet's IP Source Address are compared to match this rule. An IP packet matches the rule when the packet's IP Destination Address bitwise ANDed with the mask value defined by the prefix equals the InetDestAddr value.";
                    }
                    leaf source-port-start {
                        type inet:port-number;
                        default 0;
                        description "This attribute represents the low-end inclusive range of TCP/UDP source port numbers to which a packet is compared. This attribute is irrelevant for non-TCP/UDP IP packets.";
                    }
                    leaf source-port-end {
                        type inet:port-number;
                        default 65535;
                        description "This attribute represents the high-end inclusive range of TCP/UDP source port numbers to which a packet is compared. This attribute is irrelevant for non-TCP/UDP IP packets.";
                    }
                    leaf destination-port-start {
                        type inet:port-number;
                        default 0;
                        description "This attribute represents the low-end inclusive range of TCP/UDP destination port numbers to which a packet is compared. This attribute is irrelevant for non-TCP/UDP IP packets.";
                    }
                    leaf destination-port-end {
                        type inet:port-number;
                        default 65535;
                        description "This attribute represents the high-end inclusive range of TCP/UDP destination port numbers to which a packet is compared. This attribute is irrelevant for non-TCP/UDP IP packets.";
                    }
                    leaf destination-mac-address {
                        type yang:mac-address;
                        default 00:00:00:00:00:00;
                        description "This attribute represents the criteria to match against an Ethernet frame MAC address bitwise ANDed with DestMacMask.";
                    }
                    leaf destination-mac-mask {
                        type yang:mac-address;
                        default 00:00:00:00:00:00;
                        description "An Ethernet frame matches an entry when its destination MAC address bitwise ANDed with the DestMacMask attribute equals the value of the DestMacAddr attribute.";
                    }
                    leaf source-mac-address {
                        type yang:mac-address;
                        default FF:FF:FF:FF:FF:FF;
                        description "This attribute represents the value to match against an Ethernet frame source MAC address.";
                    }
                    leaf ethernet-protocol-id {
		        type ethernet-protocol-id-type;
                        default none;
                        description 
                            "This attribute indicates the format of the layer 3 protocol ID in the Ethernet frame.";
                    }
                    leaf ethernet-protocol {
                        type uint16;
                        default 0;
                        description "This attribute represents the Ethernet protocol type to be matched against the frames. For EnetProtocolType set to 'none', this attribute is ignored when considering whether a packet matches the current rule. If the attribute EnetProtocolType is 'ethertype', this attribute gives the 16-bit value of the EtherType that the packet must match in order to match the rule. If the attribute EnetProtocolType is 'dsap', the lower 8 bits of this attribute's value must match the DSAP byte of the packet in order to match the rule. If the Ethernet frame contains an 802.1p/Q Tag header (i.e., EtherType 0x8100), this attribute applies to the embedded EtherType field within the 802.1p/Q header.";
                    }
                    leaf user-priority-low {
                        type uint8 {
                            range "0..7";
                        }
                        default 0;
                        description "This attribute applies only to Ethernet frames using the 802.1p/Q tag header (indicated with EtherType 0x8100). Such frames include a 16-bit Tag that contains a 3-bit Priority field and a 12-bit VLAN number. Tagged Ethernet frames must have a 3-bit Priority field within the range of PriLow to PriHigh in order to match this rule.";
                    }
                    leaf user-priority-high {
                        type uint8 {
                            range "0..7";
                        }
                        default 7;
                        description "This attribute applies only to Ethernet frames using the 802.1p/Q tag header (indicated with EtherType 0x8100). Such frames include a 16-bit Tag that contains a 3-bit Priority field and a 12-bit VLAN number. Tagged Ethernet frames must have a 3-bit Priority field within the range of PriLow to PriHigh in order to match this rule.";
                    }
                    leaf vlan-id {
                        type uint16 {
                            range "0 | 1..4094";
                        }
                        default 0;
                        description "This attribute applies only to Ethernet frames using the 802.1p/Q tag header. Tagged packets must have a VLAN Identifier that matches the value in order to match the rule.";
                    }
                    leaf flow-label {
                        type uint32 {
                            range "0..1048575";
                        }
                        default 0;
                        description 
                            "This attribute represents the Flow Label field in the IPv6 header to be matched by the classifier.
                             The value zero indicates that the Flow Label is not specified as part of the classifier and is not matched against packets.";
                    }
                    leaf cm-interface-mask {
                        type bits {
                            bit eCm {
                                position 0;
                            }
                            bit cmci {
                                position 1;
                            }
                            bit docsCableMacLayer {
                                position 2;
                            }
                            bit docsCableDownstream {
                                position 3;
                            }
                            bit docsCableUpstream {
                                position 4;
                            }
                            bit unused-5 {
                                position 5;
                            }
                            bit unused-6 {
                                position 6;
                            }
                            bit unused-7 {
                                position 7;
                            }
                            bit unused-8 {
                                position 8;
                            }
                            bit unused-9 {
                                position 9;
                            }
                            bit unused-10 {
                                position 10;
                            }
                            bit unused-11 {
                                position 11;
                            }
                            bit unused-12 {
                                position 12;
                            }
                            bit unused-13 {
                                position 13;
                            }
                            bit unused-14 {
                                position 14;
                            }
                            bit unused-15 {
                                position 15;
                            }
                            bit eMta {
                                position 16;
                            }
                            bit eStbIp {
                                position 17;
                            }
                            bit eStbDsg {
                                position 18;
                            }
                        }
                        description "This attribute represents a bit-mask of the CM in-bound interfaces to which this classifier applies. This attribute only applies to upstream Drop Classifiers being sent to CMs during the registration process.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container docs-qos {
                description "This group of configuration elements allows for the configuration of DOCSIS QoS.";
                list service-class {
                    key service-class-name;
                    min-elements 0;
                    description "This object describes a provisioned service class on a CCAP. Each object instance defines a template for certain DOCSIS QOS Parameter Set values. When a CM creates or modifies an Admitted QOS Parameter Set for a Service Flow, it may reference a Service Class Name instead of providing explicit QOS Parameter Set values. In this case, the CCAP populates the QOS Parameter Set with the applicable corresponding values from the named Service Class. Subsequent changes to a Service Class row do not affect the QOS Parameter Set values of any service flows already admitted. A service class template applies to only a single direction, as indicated in the ServiceClassDirection attribute.";
                    reference 
                        "DOCSIS 3.0 Operations Support System Interface Specification
                         CM-SP-OSSIv3.0-I15-110623 ServiceClass Object section.";
                    leaf service-class-name {
                        type string {
                            length "1..15";
                        }
                        description "This key indicates the Service Class Name associated with this object instance. DOCSIS specifies that the maximum size is 16 ASCII characters including a terminating zero. The terminating zero is not represented in this SnmpAdminString syntax attribute.
";
                        reference 
                            "DOCSIS 3.0 MAC and Upper Layer Protocols Interface Specification 
                             CM-SP-MULPIv3.0-I16-110623 Service Class Name section in the Common Radio Frequency Interface Encodings Annex";
                    }
                    leaf priority {
                        type uint8;
                        default 0;
                        description "This attribute is the template for the Priority attribute of the QoS Parameter Set.";
                    }
                    leaf max-traffic-rate {
                        type uint32 {
                            range "0..4294967295";
                        }
                        units bps;
                        default 0;
                        description "This attribute is the template for the MaxTrafficRate attribute of the QoS Parameter Set.";
                    }
                    leaf max-traffic-burst {
                        type uint32;
                        units bytes;
                        default 3044;
                        description "This attribute is the template for the MaxTrafficBurst attribute of the QoS Parameter Set.";
                    }
                    leaf min-reserved-rate {
                        type uint32 {
                            range "0..4294967295";
                        }
                        units bps;
                        default 0;
                        description "This attribute is the template for the MinReservedRate attribute of the QoS Parameter Set.";
                    }
                    leaf min-reserved-packet {
                        type uint16;
                        units bytes;
                        mandatory true;
                        description "This attribute is the template for the MinReservedPkt attribute of the QoS Parameter Set.";
                    }
                    leaf max-concatenated-burst {
                        type uint16;
                        units bytes;
                        default 1522;
                        description "This attribute is the template for the MaxConcatBurst attribute of the QoS Parameter Set.";
                    }
                    leaf nominal-polling-interval {
                        type uint32;
                        units microseconds;
                        default 0;
                        description "This attribute is the template for the NomPollInterval attribute of the QoS Parameter Set.";
                    }
                    leaf tolerated-poll-jitter {
                        type uint32;
                        units microseconds;
                        default 0;
                        description "This attribute is the template for the TolPolJitter attribute of the QoS Parameter Set.";
                    }
                    leaf unsolicited-grant-size {
                        type uint16;
                        units bytes;
                        default 0;
                        description "This attribute is the template for the UnsolicitGrantSize attribute of the QoS Parameter Set.";
                    }
                    leaf nominal-grant-interval {
                        type uint32;
                        units bytes;
                        default 0;
                        description "This attribute is the template for the NomGrantInterval attribute of the QoS Parameter Set.";
                    }
                    leaf tolerated-grant-jitter {
                        type uint32;
                        units microseconds;
                        default 0;
                        description "This attribute is the template for the TolGrantJitter attribute of the QoS Parameter Set.";
                    }
                    leaf grants-per-interval {
                        type uint8;
                        units dataGrants;
                        default 0;
                        description "This attribute is the template for the GrantsPerInterval attribute of the QoS Parameter Set.";
                    }
                    leaf max-latency {
                        type uint32;
                        units microseconds;
                        default 0;
                        description "This attribute is the template for the MaxLatency attribute of the QoS Parameter Set.";
                    }
                    leaf active-timeout {
                        type uint16;
                        units seconds;
                        default 0;
                        description "This attribute is the template for the ActiveTimeout attribute of the QoS Parameter Set.";
                    }
                    leaf admitted-timeout {
                        type uint16;
                        units seconds;
                        default 200;
                        description "This attribute is the template for the AddmitedTimeout attribute of the QoS Parameter Set.";
                    }
                    leaf scheduling-type {
		        type service-flow-scheduling-type;
                        default best-effort;
                        description "This attribute is the template for the SchedulingType attribute of the QoS Parameter Set.";
                    }
                    leaf request-policy {
                        type ccap-octet-data-type {
                            length "8";
                        }
                        default 00000000;
                        description "This attribute is the template for the RequestPolicyOct attribute of the QoS Parameter Set.";
                    }
                    leaf tos-and-mask {
                        type ccap-octet-data-type {
                            length "2";
                        }
                        mandatory true;
                        description "This attribute is the template for the TosAndMask attribute of the QoS Parameter Set.";
                    }
                    leaf tos-or-mask {
                        type ccap-octet-data-type {
                            length "2";
                        }
                        mandatory true;
                        description "This attribute is the template for the TosOrMask attribute of the QoS Parameter Set.";
                    }
                    leaf direction {
		        type direction-type;
                        default upstream;
                        description "This attribute is the template for the Direction attribute of the QoS Parameter Set.";
                    }
                    leaf dscp-overwrite {
                        type int32 {
                            range "-1 | 0..63";
                        }
                        default -1;
                        description 
                            "This attribute allows the overwrite of the DSCP field per RFC 3260.
                             If this attribute is -1, then the corresponding TosAndMask value is set to be 'FF'H and TosOrMask is set to '00'H. Otherwise, this attribute is in the range of 0..63, and the corresponding TosAndMask value is '03'H and TosOrMaskvalue is this attribute value shifted left by two bit positions.";
                    }
                    leaf required-attribute-mask {
                        type attribute-mask-type;
                        description "This attribute is the template for the RequiredAttrMask attribute of the QoS Parameter Set.";
                    }
                    leaf forbidden-attribute-mask {
                        type attribute-mask-type;
                        description "This attribute is the template for the ForbiddenAttrMask attribute of the QoS Parameter Set.";
                    }
                    leaf attribute-aggregate-rule-mask {
                        type ccap-octet-data-type {
                            length "8";
                        }
                        default 00000000;
                        description "This attribute is the template for the AttrAggregationMask attribute of the QoS Parameter Set.";
                    }
                    leaf application-id {
                        type uint32;
                        mandatory true;
                        description "This attribute is the template for the AppId attribute of the QoS Parameter Set.";
                    }
                    leaf multiplier-contention-request-window {
                        type uint8 {
                            range "4..12";
                        }
                        units eighths;
                        default 8;
                        description "This attribute is the template for the MultiplierContentionReqWindow attribute of the QoS Parameter Set.";
                    }
                    leaf multiplier-bytes-requested {
                        type uint8 {
                            range "1 | 2 | 4 | 8 | 16";
                        }
                        default 4;
                        description "This attribute is the template for the MultiplierBytesReq attribute of the QoS Parameter Set.";
                    }
                    leaf max-requests-per-sid-cluster {
                        type uint8;
                        units requests;
                        default 0;
                        description 
                            "This attribute is the template for the MaxReqPerSidCluster attribute of the QoS Parameter Set.
                             This attribute has been deprecated and replaced with MaxReqPerSidCluster in the ServiceFlow object.";
                    }
                    leaf max-outstanding-bytes-per-sid-cluster {
                        type uint32;
                        units bytes;
                        default 0;
                        description 
                            "This attribute is the template for the MaxOutstandingBytesPerSidCluster attribute of the QoS Parameter Set.
                             This attribute has been deprecated and replaced with MaxOutstandingBytesPerSidCluster in the ServiceFlow object.";
                    }
                    leaf max-total-bytes-requested-per-sid-cluster {
                        type uint32;
                        units bytes;
                        default 0;
                        description 
                            "This attribute is the template for the MaxTotBytesReqPerSidCluster attribute of the QoS Parameter Set.
                             This attribute has been deprecated and replaced with MaxTotBytesReqPerSidCluster in the ServiceFlow object.";
                    }
                    leaf max-time-in-sid-cluster {
                        type uint16;
                        units milliseconds;
                        default 0;
                        description 
                            "This attribute is the template for the MaxTimeInSidCluster attribute of the QoS Parameter Set.
                             This attribute has been deprecated and replaced with MaxTimeInSidCluster in the ServiceFlow object.";
                    }
                    leaf peak-traffic-rate {
                        type uint32;
                        units bps;
                        default 0;
                        description "This attribute is the template for the PeakTrafficRate attribute of the QoS Parameter Set.";
                    }
                    leaf ds-resequencing {
		        type ds-resequencing-type;
                        default resequencing-dsid;
                        description "This attribute is the template for the DsResequencing attribute of the QoS Parameter Set.";
                    }
                    leaf minimum-buffer {
                        type uint32;
                        units bytes;
                        default 0;
                        description "This attribute is the template for the MinimumBuffer attribute of the QoS Parameter Set.";
                    }
                    leaf target-buffer {
                        type uint32;
                        units bytes;
                        default 0;
                        description "This attribute is the template for the TargetBuffer attribute of the QoS Parameter Set.";
                    }
                    leaf maximum-buffer {
                        type uint32;
                        units bytes;
                        default 4294967295;
                        description "This attribute is the template for the MaximumBuffer attribute of the QoS Parameter Set.";
                    }
                    container yang-ext {
                        ccap:extensionPoint; //different pyang flags impact use of this hint
                        description "node for vendor YANG extensions";
                    }
                }
                list qos-profile {
                    key qos-profile-index;
                    description "The qos-profile object is used to help provide a mapping between Cable Modems that have registered with a DOCSIS 1.0 style Class of Service. The support for this configuration is dependent on the CCAP supporting DOCSIS 1.0 style configuration files and CM registrations. ";
                    reference "RFC 4546 docsIfQosProfileTable";
                    leaf qos-profile-index {
                        type uint16 {
                            range "1..16383";
                        }
                        description "This attribute configures an unique index for each instance of this object.";
                    }
                    leaf priority {
                        type uint8 {
                            range "0..7";
                        }
                        default 0;
                        description "This attribute configures the DOCSIS priority for this service flow.";
                    }
                    leaf max-up-bandwidth {
                        type uint32 {
                            range "0..100000000";
                        }
                        units bps;
                        default 0;
                        description "This attribute configures the maximum upstream bandwidth, in bits per second, allowed for a service with this service class. The value zero is used if there is no restriction of upstream bandwidth.";
                    }
                    leaf guaranteed-up-bandwidth {
                        type uint32 {
                            range "0..100000000";
                        }
                        units bps;
                        default 0;
                        description "This attribute configures the minimum guaranteed upstream bandwidth, in bits per second allowed for a service with this service class.";
                    }
                    leaf max-down-bandwidth {
                        type uint32 {
                            range "0..100000000";
                        }
                        units bps;
                        default 0;
                        description "This attribute configures the maximum downstream bandwidth, in bits per second allowed for a service with this service class. The value of zero is used if there is no restriction of downstream bandwidth.";
                    }
                    leaf baseline-privacy {
                        type boolean;
                        default false;
                        description "This attribute configures BPI encryption for this service class.";
                    }
                    leaf max-transmit-burst {
                        type uint16;
                        units bytes;
                        default 0;
                        description "This attribute configures the maximum number of bytes that may be requested for a single upstream transmission.  A value of zero means there is no limit.  Note: This value does not include any physical layer overhead.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container docs-multicast-qos {
                description "This group of configuration elements allows for the configuration of DOCSIS Multicast QoS. They are based on the configuration elements from [OSSIv3.0].";
                leaf default-group-service-class {
                    type leafref {
                        path "../../docs-qos/service-class/service-class-name";
                    }
                    description "This object provides the name of the Default Group Service Class. The CCAP instantiates a Default Group Service Flow with the QOS param Set indicated by this Service Class Name reference on every Downstream Channel Set to which it replicates multicast packets that are otherwise unclassified by a Group Classifier Rule.
Reference: [OSSIv3.0], DefGrpSvcClass Object section";
                }
                list group-phs-config {
                    key group-phs-config-id;
                    min-elements 0;
                    description 
                        "This object controls the configuration of DSID-indexed PHS for multicast sessions. Configuration of PHS Rules via this object are applied to individual multicast sessions even if the referenced GrpCfg object identified a GrpQosCfg instance with a QosCtrl of 'aggregateSession'.
                         This object supports the creation and deletion of instances.
                         Creation of multiple instances of this object require the following attributes to be set:
                         - PhsField
                         - PhsMask
                         - PhsSize";
                    reference 
                        "DOCSIS 3.0 Operations Support System Interface Specification
                         CM-SP-OSSIv3.0-I15-110623 CmtsGrpPhsCfg Object section.";
                    leaf group-phs-config-id {
                        type uint16 {
                            range "1..65535";
                        }
                        mandatory true;
                        description "This attribute identifies the unique identifier of a PHS rule that is referenced by the GrpCfg object.";
                    }
                    leaf phs-field {
                        type ccap-octet-data-type {
                            length "0..510";
                        }
                        mandatory true;
                        description "This attribute defines the bytes of the DOCSIS header which must be suppressed/restored by the sending/receiving device.";
                    }
                    leaf phs-mask {
                        type ccap-octet-data-type {
                            length "0..64";
                        }
                        mandatory true;
                        description 
                            "This attribute defines the bit mask which is used in combination with the PhsField to define which bytes in header must be suppressed/restored by the sending or receiving device.
                             Each bit of this bit mask corresponds to a byte in the PhsField, with the least significant bit corresponding to the first byte of the PhsField.
                             Each bit of the bit mask specifies whether or not the corresponding byte should be suppressed in the packet. A bit value of '1' indicates that the byte should be suppressed by the sending device and restored by the receiving device.
                             A bit value of '0' indicates that the byte should not be suppressed by the sending device or restored by the receiving device.
                             If the bit mask does not contain a bit for each byte in the PhsField then the bit mask is extended with bit values of '1' to be the necessary length.";
                    }
                    leaf phs-size {
                        type uint8;
                        units bytes;
                        mandatory true;
                        description 
                            "This attribute specifies the number of bytes in the header to be suppressed and restored.
                             The value of this object matches the number of bytes the bits indicated in the PhsField attribute.";
                    }
                    leaf phs-verify {
                        type boolean;
                        default false;
                        description "This attribute specifies the Payload Header Suppression verification value of 'true' the sender must verify PhsField is the same as what is contained in the packet to be suppressed.";
                    }
                    container yang-ext {
                        ccap:extensionPoint; //different pyang flags impact use of this hint
                        description "node for vendor YANG extensions";
                    }
                }
                list group-config {
                    key group-config-id;
                    min-elements 0;
                    description 
                        "This object controls the QoS, PHS, and encryption settings for downstream forwarding of IP multicast sessions. An IP multicast session is replicated to one or more Downstream Channel Sets (DCSs), where each DCS is either a single downstream channel or a downstream bonding group of multiple channels. The CCAP determines on which DCSs to replicate a multicast session based on IP multicast membership reports (joins) or other vendor-specific static configuration. 
                         The CmtsGrpCfg object allows for the configuration of a range of sessions through the SrcPrefixAddr and GrpPrefixAddr and SrcPrefixLen and GrpPrefixLen attributes. 
                         Cable operators can specify configuration rules for a range of multicast sessions through the tuples of (SrcPrefixAddr, SrcPrefixLen, GrpPrefixAddr, GrpPrefixLen) attributes in an entry. The QosCfgId attribute identifies the QoS rule, the EncryptCfgId identifies the encryption rule and the PhsCfgId identifies the PHS rule for a particular entry. Even if an entry indicates a range of multicast sessions, the Encryption and PHS rules are applied on a per-session basis. Thus, when an Operator configures PHS rules or Encryption for a given GroupConfig entry, each session has those rules applied on a per session and per replication basis. Group PHS and Group Encryption rules are indicated by using a non-zero value for the PhsCfgId and EncryptCfgId, respectively.
                         The DocsMcastCmtsGrpQosCfgQosCtrl attribute from the CmtsGrpQosCfg object is used to determine if the traffic for a range of multicast sessions identified by an entry in the CmtsGrpCfg object will be transmitted in an Aggregate-Session Group Service Flow or will be transmitted separately for each session using Single-Session Group Service Flows. Even if the range of multicast sessions are transmitted on an Aggregate-Session Group Service Flow, the PHS and Encryption rules are always applied individually to a multicast session on a per-session DSID basis prior to being transmitted on an Aggregate-Session Group Service Flow (GSF).
                         Creation of a new instance of this object requires the following attributes to be set.
                         - RulePriority
                         - SrcPrefixAddr
                         - GrpPrefixAddr
                         - TosLow
                         - TosHigh
                         - TosMask";
                    reference 
                        "DOCSIS 3.0 Operations Support System Interface Specification
                         CM-SP-OSSIv3.0-I15-110623 CmtsGrpCfg Object section.";
                    leaf group-config-id {
                        type uint32 {
                            range "1..4294967295";
                        }
                        description "This attribute represents the unique identifier of instances of this object. This attribute is the key that identifies unique instances of the group-config Object.";
                    }
                    leaf rule-priority {
                        type uint8;
                        mandatory true;
                        description "This attribute indicates the priority of this entry used to resolve which instance of this object apply when a newly replicated multicast session matches multiple entries. Higher values indicate a higher priority. Valid values for this attribute are 0..63 and 192..255 in order to not conflict with CMTS internally-created instances that use the range 64..191.";
                    }
                    uses ssm-group;
                    leaf tos-low {
                        type ccap-octet-data-type {
                            length "2";
                        }
                        mandatory true;
                        description 
                            "This attribute identifies the low value of a range of the TOS byte value to be defined in a packet classifier this GC instantiates in the GCR in order to limit the GCR-matched traffic to a particular set of DSCPs. This applies to the IPv4 TOS byte and the IPv6 Traffic Class byte.
                             The IP TOS octet, as originally defined in [RFC 791], has been superseded by the 6-bit Differentiated Services Field and the 2-bit Explicit Congestion Notification Field.";
                        reference "RFC 791; RFC 3260; RFC 3168.";
                    }
                    leaf tos-high {
                        type ccap-octet-data-type {
                            length "2";
                        }
                        mandatory true;
                        description 
                            "This attribute identifies the high value of a range of the TOS byte value to be defined in a packet classifier this GC instantiates in the GCR in order to limit the GCR-matched traffic to a particular set of DSCPs. This applies to the IPv4 TOS byte and the IPv6 Traffic Class byte.
                             The IP TOS octet, as originally defined in [RFC 791], has been superseded by the 6-bit Differentiated Services Field (DSField, [RFC 3260]) and the 2-bit Explicit Congestion Notification Field (ECN field, [RFC 3168]).";
                        reference "RFC 791; RFC 3260; RFC 3168.";
                    }
                    leaf tos-mask {
                        type ccap-octet-data-type {
                            length "2";
                        }
                        mandatory true;
                        description 
                            "This attribute identifies the mask value bitwise ANDed with a TOS byte value to be defined in a packet classifier this GC instantiates in the GCR in order to limit the GCR-matched traffic to a particular set of DSCPs. This applies to the IPv4 TOS byte and the IPv6 Traffic Class byte.
                             The IP TOS octet, as originally defined in [RFC 791], has been superseded by the 6-bit Differentiated Services Field (DSField, [RFC 3260]) and the 2-bit Explicit Congestion Notification Field (ECN field, [RFC 3168]).";
                        reference "RFC 791; RFC 3260; RFC 3168.";
                    }
                    leaf group-qos-config-id {
                        type leafref {
                            path "../../group-qos-config/group-qos-config-id";
                        }
                        description "This attribute identifies an instance in CmtsGrpQosCfg for configuring the QoS for the replication of the sessions matching this CmtsGrpCfg instance.
";
                    }
                    leaf group-encryption-config-id {
                        type leafref {
                            path "../../group-encryption-config/group-encryption-config-id";
                        }
                        description "This attribute identifies an instance in CmtsGrpEncryptCfg for configuring the encryption of replications derived from this GC.";
                    }
                    leaf group-phs-config-id {
                        type leafref {
                            path "../../group-phs-config/group-phs-config-id";
                        }
                        description "This attribute identifies an instance in CmtsGrpPhsCfg that configures DSID-indexed PHS compression for all replications derived from this GC.";
                    }
                    container yang-ext {
                        ccap:extensionPoint; //different pyang flags impact use of this hint
                        description "node for vendor YANG extensions";
                    }
                }
                list group-encryption-config {
                    key group-encryption-config-id;
                    description "This object controls the configuration of the Security Association (SA) and the encryption algorithm used for multicast sessions.

";
                    reference 
                        "DOCSIS 3.0 Operations Support System Interface Specification
                         CM-SP-OSSIv3.0-I15-110623 CmtsGrpEncryptCfg Object section.";
                    leaf group-encryption-config-id {
                        type uint16;
                        description "This attribute specifies the unique identifier of instances of this object.";
                    }
                    leaf control {
		        type encryption-algorithm-ctl-type;
                        default mgmt;
                        description "This attribute controls whether the CMTS can select the encryption algorithm or if this can be set manually using the Alg attribute.";
                    }
                    leaf algorithm {
		        type encryption-algorithm-type;
                        default des56-cbc-mode;
                        description "This attribute defines which encryption algorithm will be used for an SA referenced by this object when the Ctrl is set to 'mgmt'.";
                    }
                    container yang-ext {
                        ccap:extensionPoint; //different pyang flags impact use of this hint
                        description "node for vendor YANG extensions";
                    }
                }
                list group-qos-config {
                    key group-qos-config-id;
                    min-elements 0;
                    description 
                        "This object configures the QoS configured for Multicast sessions replicated to any Downstream Channel Set. It does not control which particular DCSs to which the CCAP replicates a multicast session. 
                         An instance of this object is called a GQC entry. A GQC entry controls how the CCAP instantiates a Group Classifier Rule (GCR) on the DCS to match packets of the multicast session. A GCR uses source and destination IP address and ToS criteria.
                         A GQC entry controls how and with what QoS parameters a GSF is created on a DCS. All downstream multicast packets are scheduled on a GSF. The QoS Type attribute of the GQC entry controls whether the CCAP creates one GSF for each single IP multicast session or whether the CCAP creates one GSF for the aggregate of all sessions that match the GQC criteria. The GQC instance contains a reference to a Service Class Name QoS Parameter Set template. The Service Class defines the list of QoS parameters for the GSF(s) instantiated for the GQC entry. 
                         A CCAP identifies one Service Class as the Default Group QoS Service Class. The CCAP instantiates a Default Group Service Flow on each single-channel DCS based on the parameters of the Default Group QoS Service Class. 
                         The set of GCRs and GSFs instantiated on a DCS control how QoS is provided to multicast packets replicated to the DCS. For each multicast packet, the CCAP classifies the packet to the highest priority matching GCR on that DCS. The GCR refers to a single GSF, which controls the scheduling of the packets on the DCS. If the multicast packet does not match any GCR on the DCS, the packet is scheduled on the Default Group Service Flow of the DCS. The CCAP replicates unclassified multicast traffic to only DCSs consisting of a single downstream channel. Thus, the Maximum Sustained Traffic Rate QoS parameter of the Default Group Service Class limits the aggregate rate of unclassified multicast traffic on each downstream channel. 
                         The CCAP is expected to instantiate GCRs and GSFs controlled by the entries in this table only for the duration of replication of the multicast sessions matching the entry.
                         This object supports the creation of multiple instances.
                         Creation of new instances of this object require the following objects to be set:
                         - SvcClassName
                         - QosCtrl
                         - AggSessLimit";
                    reference 
                        "DOCSIS 3.0 Operations Support System Interface Specification
                         CM-SP-OSSIv3.0-I15-110623 CmtsGrpQosCfg Object section.";
                    leaf group-qos-config-id {
                        type uint16;
                        mandatory true;
                        description "This attribute identifies a unique Group QoS Configuration object instance.";
                    }
                    leaf service-class-name {
                        type leafref {
                            path "/ccap/docsis/docs-qos/service-class/service-class-name";
                        }
                        mandatory true;
                        description "Reference to the Service Class Name.";
                    }
                    leaf qos-control {
                        type qos-control-type;
                        mandatory true;
                        description "This attribute identifies how Group Classifier Rules (GCRs) and Group Service Flows (GSFs) are instantiated when multiple sessions match the (S,G) criteria of this entry.";
                    }
                    leaf aggregated-session-limit {
                        type uint16 {
                            range "1.. 65535";
                        }
                        units sessions;
                        mandatory true;
                        description "This attribute identifies the maximum number of sessions that may be aggregated in an aggregated Service Flow. This value is ignored in case of a GQC entry with QosCtrl set to 'singleSession'.";
                    }
                    leaf application-id {
                        type uint32;
                        default 0;
                        description 
                            "This attribute allows the operator to configure a Cable Operator defined Application Identifier for multicast sessions, e.g., an Application Manager ID and Application Type. This Application Identifier can be used to influence admission control or other policies in the CMTS that are outside of the scope of this specification. This parameter is optional in defining QoS for multicast sessions.
                             If the value of this attribute is different from the value of the AppId in the referenced SCN for this GQC instance, the value of this attribute is used.";
                        reference 
                            "DOCSIS 3.0 MAC and Upper Layer Protocols Interface Specification 
                             CM-SP-MULPIv3.0-I16-110623 Application Identifier section in the Common Radio Frequency Interface Encodings Annex
                             PacketCable Multimedia Specification PKT-SP-MM-I05-091029 Policy Server and CMTS Interface section.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            choice remote-query {
	            case cm-remote-query {
	                leaf enable {
	                    type boolean;
	                    default false;
	                }
	                leaf snmp-community {
	                    type string {
	                        length "1..32";
	                    }
	                    mandatory true;
	                }
	                leaf polling-interval {
	                    type uint32;
	                    units "seconds";
	                    description "This attribute configures the minimum amount of time in seconds
	                        between consecutive polls of the same MIB object on the same cable modem.";
	                }
	                leaf source-ip-interface-name {
	                    type string;
	                    description "Local IP interface; must be a configured ip-interface name. If not specified, then the vendor picks the source IP address.
	                           The source interface address used, when configured, is the configured PrimaryIpv4 or (one of) Global Scope Ipv6 address for the specified interface.";
	                }
                    container yang-ext4 {
                        ccap:extensionPoint; //different pyang flags impact use of this hint
                        description "node for vendor YANG extensions";
                    }
	            }
            }
            container docs-mac-domain {
                description "This container contains MAC domain level control and configuration.";
                list downstream-bonding-group {
                    key bonding-group-name;
                    min-elements 0;
                    description "The downstream-bonding-group object allows for the static creation of Downstream bonding groups. In some current DOCSIS 3.0 configurations, downstream channels are not tied directly to a specific MAC domain, while in others these downstream channels are an integral part of the MAC domain. For CCAP flexibility, downstream channels that are configured into a bonding group will not be directly associated with a specific MAC domain.";
                    leaf bonding-group-name {
                        type string;
                        description "The name of the bonding group.";
                    }
                    leaf sf-provisioned-attribute-mask {
                       type attribute-mask-type;
                       default bonded;
                       description "This attribute represents the Provisioned Attribute Mask encoding for the bonding group.";
                    }
                    leaf dsid-resequencing-warning-threshold {
                        type uint8 {
                            range "0..179 | 255";
                        }
                        units "hundred microseconds";
                        default 255;
                        description 
                            "This attribute provides the DSID Resequencing Warning Threshold in hundredMicroseconds that is to be used for all DSIDs associated with this Downstream Bonding Group. The value of 255 indicates that the DSID Resequencing Warning Threshold is determined by the CMTS. The value of 0 indicates that the threshold warnings are disabled. 
                             When the value of DsidReseqWaitTime is not equal to 0 or 255, the CCAP will ensure that the value of this object is either 255 or less than the value of DsidReseqWaitTime.";
                    }
                    leaf dsid-resequencing-wait-time {
                        type uint8 {
                            range "1..180 | 255";
                        }
                        units "hundred microseconds";
                        default 255;
                        description "This attribute provides the DSID Resequencing Wait Time in hundredMicroseconds that is to be used for all DSIDs associated with this Downstream Bonding Group. The value of 255 indicates that the DSID Resequencing Wait Time is determined by the CMTS.";
                    }
                    list docsis-down-channel-ref {
                        key "slot ds-rf-port down-channel";
                        description "A reference to a DOCSIS downstream channel.";
                        ccap:inlineType;
                        uses docsis-down-channel-reference;
                        container yang-ext {
                            ccap:extensionPoint; //different pyang flags impact use of this hint
                            description "node for vendor YANG extensions";
                        }
                    }
                    leaf downstream-bonding-mac-domain-name {
                        type leafref {
                            path "../../mac-domain/mac-domain-name";
                        }
                        description "The name of the MacDomain.";
                    }
                    container yang-ext {
                        ccap:extensionPoint; //different pyang flags impact use of this hint
                        description "node for vendor YANG extensions";
                    }
                }
                list deny-cm {
                    key device-mac-address;
                    leaf device-mac-address {
                        type yang:mac-address;
                        description "The MAC address of the CM that will be added to the deny list.";
                    }
                    container yang-ext {
                        ccap:extensionPoint; //different pyang flags impact use of this hint
                        description "node for vendor YANG extensions";
                    }
                }
                list mac-domain {
                    key mac-domain-name;
                    min-elements 0;
                    description "Mac-domain contains MAC domain level control and configuration attributes.";
                    reference 
                        "DOCSIS 3.0 Operations Support System Interface Specification
                         CM-SP-OSSIv3.0-I15-110623 MdCfg Object section.";
                    uses mac-domain-configuration-group;
                    leaf mdd-interval {
                        type uint16 {
                            range "1..2000";
                        }
                        units milliseconds;
                        default 2000;
                        description 
                            "This attribute configures the interval for the insertion of MDD messages
                             in each downstream channel of a MAC Domain.";
                        reference 
                            "DOCSIS 3.0 Operations Support System Interface Specification
                             CM-SP-OSSIv3.0-I15-110623 MdCfg Object section.";
                    }
                    leaf cm-status-event-control-enabled {
                        type boolean;
                        default true;
                        description "If set to 'true', this attribute enables the signaling of the CM-Status Event reporting mechanism.";
                        reference 
                            "DOCSIS 3.0 Operations Support System Interface Specification
                             CM-SP-OSSIv3.0-I15-110623 MdCfg Object section.";
                    }
                    leaf upstream-frequency-range {
                        type upstream-frequency-range-type;
                        default standard;
                        description "This attribute indicates in MDD messages the upstream frequency upper band edge of an upstream Channel.";
                    }
                    leaf multicast-dsid-forward-enabled {
                        type boolean;
                        default true;
                        description "If set to 'true', this attribute enables the CMTS to use IP Multicast DSID Forwarding (MDF) for the MAC domain.";
                        reference 
                            "DOCSIS 3.0 Operations Support System Interface Specification
                             CM-SP-OSSIv3.0-I15-110623 MdCfg Object section.";
                    }
                    leaf multiple-receive-channel-mode-enabled {
                        type boolean;
                        default true;
                        description "If set to 'true', this attribute enables Downstream Channel Bonding for the MAC Domain.";
                        reference 
                            "DOCSIS 3.0 Operations Support System Interface Specification
                             CM-SP-OSSIv3.0-I15-110623 MdCfg Object section.";
                    }
                    leaf multiple-transmit-channel-mode-enabled {
                        type boolean;
                        default true;
                        description "If set to 'true', this attribute enables Multiple Transmit Channel (MTC) Mode for the MAC Domain.";
                        reference 
                            "DOCSIS 3.0 Operations Support System Interface Specification
                             CM-SP-OSSIv3.0-I15-110623 MdCfg Object section.";
                    }
                    leaf early-auth-encrypt-control {
                        type early-auth-encrypt-control-type;
                        default enable-eae-ranging-based-enforcement;
                        description "This attribute enables or disables early authentication and encryption (EAE) signaling for the MAC Domain. It also defines the type of EAE enforcement in the case that EAE is enabled.";
                    }
                    leaf tftp-proxy-enabled {
                        type boolean;
                        default true;
                        description "If set to 'true', this attribute enables TFTP Proxy functionality for the MAC Domain.";
                        reference 
                            "DOCSIS 3.0 Operations Support System Interface Specification
                             CM-SP-OSSIv3.0-I15-110623 MdCfg Object section.";
                    }
                    leaf source-address-verification-enabled {
                        type boolean;
                        default true;
                        description "If set to 'true', this attribute enables Source Address Verification (SAV) functionality for the MAC Domain.";
                        reference 
                            "DOCSIS 3.0 Operations Support System Interface Specification
                             CM-SP-OSSIv3.0-I15-110623 MdCfg Object section.";
                    }
                    leaf cm-udc-enabled {
                        type boolean;
                        default false;
                        description "If set to 'true', this attribute instructs the CMTS MAC Domain to enable Upstream Drop Classifiers (UDC) for the CMs attempting registration in this MAC Domain.";
                        reference 
                            "DOCSIS 3.0 Operations Support System Interface Specification
                             CM-SP-OSSIv3.0-I15-110623 MdCfg Object section.";
                    }
                    leaf send-udc-rules-enabled {
                        type boolean;
                        default false;
                        description 
                            "If set to 'true' and when the CM signals to the CMTS 'Upstream Drop Classifier Group ID' encodings, this attribute instructs the CMTS MAC Domain to send the Subscriber Management Filters rules associated with the 'Upstream Drop Classifier Group ID' encodings to the CM in the form of UDCs when the following conditions occurs:
                             - The attribute CmUdcEnabled value for this MAC Domain is set to 'true', and
                             - The CM has the UDC capability advertised as supported.
                             If there is no a single Subscriber Management Filter configured in the CMTS for the CM's signaled UDC Group ID, the CMTS does not send UDC encodings to the CM.
                             It is vendor specific whether the CMTS maintains enforcement of the CM signaled or default Subscriber Management Filter groups in the upstream direction.";
                        reference 
                            "DOCSIS 3.0 Operations Support System Interface Specification
                             CM-SP-OSSIv3.0-I15-110623 MdCfg Object section.";
                    }
                    leaf service-type-id-list {
                        type snmp-tag-list-type;
                        description 
                            "This attribute indicates the list of Service Type IDs associated with the MAC Domain.
                             During the CM registration process the CMTS will attempt to redirect the CM to a MAC Domain where the CM' Service Type TLV is contained in this attribute.";
                    }
                    leaf bpi2-enforce-control {
                        type bpi2-enforce-control-type;
                        default qosCfgFileWithBpi2Enabled;
                        description "This attribute indicates the level of BPI+ enforcement policies with the MAC Domain.
";
                        reference 
                            "DOCSIS 3.0 Operations Support System Interface Specification
                             CM-SP-OSSIv3.0-I15-110623 MdCfg Object section.";
                    }
                    leaf energy-mgt-1x1-enabled {
                        type boolean;
                        default false;
                        description "This attribute indicates whether the CMTS is configured for 1x1 Energy Management
                                     Mode of operation on a per MAC Domain basis. If this attribute is set to true,
                                     the CMTS is configured for 1x1 Energy Management Mode of operation on this MAC Domain.
                                     If this attribute is set to false, the Energy Management 1x1 Mode of operation
                                     is disabled in the CMTS on this MAC Domain.";
                        reference "DOCSIS 3.0 MAC and Upper Layer Protocols Interface Specification 
                                   CM-SP-MULPIv3.0-I20-121113, Energy Management Capabilities section.";
                    }
                    container md-bpi-config {
                        description "This object is based on DocsBpiCmtsBaseEntry table defined in [RFC 3083].
                                     This optional object provides the configuration of the Baseline Privacy key lifetimes for the MAC domain. If not used, the CCAP uses the defaults defined in SysBpiCfg.";
                        reference "RFC 3083";
                        leaf default-authentication-lifetime {
                            type uint32;
                            units seconds;
                            description "The value of this object is the default lifetime, in seconds, the CCAP assigns to a new authorization key.";
                        }
                        leaf default-tek-lifetime {
                            type uint32;
                            units seconds;
                            description "The value of this object is the default lifetime, in seconds, the CCAP assigns to a new Traffic Encryption Key (TEK).";
                        }
                        container yang-ext {
                            ccap:extensionPoint; //different pyang flags impact use of this hint
                            description "node for vendor YANG extensions";
                        }
                    }
                    list upstream-bonding-group {
                        key bonding-group-name;
                        min-elements 0;
                        description "The upstream-bonding-group object allows for the static creation of upstream bonding groups To configure an upstream bonding group, an instance of the UsBondingGrpCfg object is created.";
                        leaf bonding-group-name {
                            type string;
                            description "The name of the bonding group.";
                        }
                        leaf sf-provisioned-attribute-mask {
                            type attribute-mask-type;
                            default bonded;
                            description "This attribute represents the Provisioned Attribute Mask encoding for the bonding group.";
                        }
                        list upstream-logical-channel-ref {
                            key "slot us-rf-port upstream-physical-channel upstream-logical-channel";
                            min-elements 0;
                            description "This element configures an upstream logical channel to be part of this upstream bonding group.";
                            uses upstream-logical-channel-reference;
                            container yang-ext {
                                ccap:extensionPoint; //different pyang flags impact use of this hint
                                description "node for vendor YANG extensions";
                            }
                        }
                        container yang-ext {
                            ccap:extensionPoint; //different pyang flags impact use of this hint
                            description "node for vendor YANG extensions";
                        }
                    }
                    list rcc-configuration {
                        key "rcp-id rcc-cfg-id";
                        min-elements 0;
                        description 
                            "This object is based on the RccCfg object defined in [OSSIv3.0] and is used with the following modification: The MdIfIndex attribute has been removed and replaced by the named association between MdCfg and RccCfg.
                             This object creates static Receive Channel Configurations for specific downstream channel configurations, identifies the scope of the Receive Channel Configuration (RCC), and provides a top level container for the Receive Module and Receive Channel objects. The CCAP selects an instance of this object to assign to a CM when it registers.
                             This object supports the creation and deletion of multiple instances.";
                        reference 
                            "DOCSIS 3.0 Operations Support System Interface Specification
                             CM-SP-OSSIv3.0-I15-110623 RccCfg Object section.";
                        leaf rcp-id {
                            type ccap-octet-data-type {
                                length "10";
                            }
                            description "This key represents the 'Receive Channel Profile Identifier' (RCP-ID) configured for the MAC Domain indicated by this instance.";
                            reference 
                                "DOCSIS 3.0 Operations Support System Interface Specification
                                 CM-SP-OSSIv3.0-I15-110623 RccCfg Object section.";
                        }
                        leaf rcc-cfg-id {
                            type uint32 {
                                range "1..4294967295";
                            }
                            description "This key denotes an RCC combination assignment for a particular RcpId and is unique per combination of MAC Domain and RcpId.";
                            reference 
                                "DOCSIS 3.0 Operations Support System Interface Specification
                                 CM-SP-OSSIv3.0-I15-110623 RccCfg Object section.";
                        }
                        leaf vendor-specific {
                            type ccap-octet-data-type {
                                length "0..504";
                            }
                            description "This attribute contains vendor-specific information of the CM Receive Channel configuration.";
                            reference 
                                "DOCSIS 3.0 Operations Support System Interface Specification
                                 CM-SP-OSSIv3.0-I15-110623 RccCfg Object section.";
                        }
                        leaf description {
                            type string {
                                length "0..15";
                            }
                            default " ";
                            description "This attribute contains a human-readable description of the CM RCP Configuration.";
                        }
                        list receive-channel-configuration {
                            key receive-channel-id;
                            min-elements 0;
                            description 
                                "The Receive Channel Configuration object permits an operator to configure how CMs registered with certain Receive Channel Profiles will configure the Receive Channels within their profile. 
                                 When a CM registers with a Receive Channel Profile (RCP) for which all Receive Channel Indices (RcIds) are configured in the Receive Module object and all Receive Channels are configured within this object, the CCAP SHOULD use the configuration within these objects to set the Receive Channel Configuration returned to the CM in a REG-RSP message. 
                                 The CCAP MAY require configuration of all pertinent Receive Module and Receive Channel instances in order to register a CM that reports a Receive Channel Profile (RCP), including any standard Receive Channel Profiles. 
                                 If the CM reports multiple RCPs, and Receive Module and Receive Channel objects have instances for more than one RCP, the particular RCP selected by the CCAP is not specified. A CCAP is not restricted to assigning Receive Modules based only on the contents of this object.";
                            leaf receive-channel-id {
                                type uint8 {
                                    range "1..255";
                                }
                                description "This key represents an identifier for the parameters of the Receive Channel instance within the Receive Channel Profile.";
                                reference 
                                    "DOCSIS 3.0 Operations Support System Interface Specification
                                     CM-SP-OSSIv3.0-I15-110623 RxChCfg Object section.";
                            }
                            leaf primary-downstream-indicator {
                                type primary-ds-indicator-type;
                                default not-specified;
                                description "If set to primary-ds-chanel, this attribute indicates the Receive Channel is to be the primary-capable downstream channel for the CM receiving this RCC. If set to backup-primary-channel, then this is the backup primary-capable downstream channel. If set to not-specified, the downstream channel is to be a non-primary-capable channel.";
                                reference 
                                    "DOCSIS 3.0 Operations Support System Interface Specification
                                     CM-SP-OSSIv3.0-I15-110623 RxChCfg Object section.";
                            }
                            leaf rc-rm-connectivity-identifier {
                                type leafref {
                                    path "../../receive-module-configuration/receive-module-id";
                                }
                                description "This attribute indicates the Receive Module (via the RmId from the RxModule object) to which this Receive Channel connects. If this object contains a zero value (and thus no Receive Channel Connectivity), the Receive Channel Connectivity TLV is omitted from the RCC.";
                                reference 
                                    "DOCSIS 3.0 Operations Support System Interface Specification
                                     CM-SP-OSSIv3.0-I15-110623 RxChCfg Object section.";
                            }
                            container docsis-down-channel-ref {
                                description "A reference to a DOCSIS downstream channel.";
                                ccap:inlineType;
                                uses docsis-down-channel-reference;
                                container yang-ext {
                                    ccap:extensionPoint; //different pyang flags impact use of this hint
                                    description "node for vendor YANG extensions";
                                }
                            }
                            container yang-ext {
                                ccap:extensionPoint; //different pyang flags impact use of this hint
                                description "node for vendor YANG extensions";
                            }
                        }
                        list receive-module-configuration {
                            key receive-module-id;
                            min-elements 0;
                            description 
                                "The Receive Module Configuration object permits an operator to configure how CMs with certain RCPs will configure the Receive Modules within their profile upon CM registration. 
                                 When a CM registers with an RCP for which all Receive Module Indices (RmIds) are configured in this object and all Receive Channels are configured within the Receive Channel (RxCh) object, the CCAP SHOULD use the configuration within these objects to set the Receive Channel Configuration assigned to the CM in a REG-RSP message. 
                                 The CCAP MAY require configuration of all pertinent Receive Module and Receive Channel instances in order to register a CM that reports a Receive Channel Profile. 
                                 If the CM reports multiple RCPs, and Receive Module and Receive Channel objects have instances for more than one RCP reported by the CM, the particular RCP selected by the CCAP is not specified. A CCAP is not restricted to assigning Receive Modules based only on the contents of this object.";
                            leaf receive-module-id {
                                type uint8 {
                                    range "1..255";
                                }
                                description "This key represents an identifier of a Receive Module instance within the Receive Channel Profile.";
                                reference 
                                    "DOCSIS 3.0 Operations Support System Interface Specification
                                     CM-SP-OSSIv3.0-I15-110623 RxModuleCfg Object section.";
                            }
                            leaf rm-rm-connectivity-id {
                                type leafref {
                                    path "../../receive-module-configuration/receive-module-id";
                                }
                                description 
                                    "This attribute represents the higher level (i.e., closer to RF) Receive Module to which this Receive Module connects. If this object contains a zero value (and thus no Receive Module Connectivity), the Receive Module Connectivity TLV is omitted from the RCC.
                                     Within a single instance of the RxModule object, the RmRmConnectivityId attribute cannot contain the same value as the RmId attribute. The RmRmConnectivityId attribute points to a separate RxModule object instance with the same value of RccCfgId.";
                                reference 
                                    "DOCSIS 3.0 Operations Support System Interface Specification
                                     CM-SP-OSSIv3.0-I15-110623 RxModuleCfg Object section.";
                            }
                            leaf first-center-frequency {
                                type uint32;
                                units hertz;
                                default 0;
                                description "This attribute represents the center frequency, in Hz, and a multiple of 62500, that indicates the low frequency channel of the Receive Module, or 0 if not applicable to the Receive Module.";
                                reference 
                                    "DOCSIS 3.0 Operations Support System Interface Specification
                                     CM-SP-OSSIv3.0-I15-110623 RxModuleCfg Object section.";
                            }
                            container yang-ext {
                                ccap:extensionPoint; //different pyang flags impact use of this hint
                                description "node for vendor YANG extensions";
                            }
                        }
                        container yang-ext {
                            ccap:extensionPoint; //different pyang flags impact use of this hint
                            description "node for vendor YANG extensions";
                        }
                    }
                    choice cmts-mac-interface {
	                    case cmts-mac-interface-config {
	                        description "This object describes the attributes of each CMTS MAC interface.";
	                        reference "RFC 4546 docsIfCmtsMacTable";
	                        leaf sync-interval {
	                            type uint8 {
	                                range "1..200";
	                            }
	                            units milliseconds;
	                            mandatory true;
	                            description "The interval between CMTS transmission of successive SYNC messages at this interface.";
	                            reference "RFC 4546";
	                        }
	                        leaf ucd-interval {
	                            type uint16 {
	                                range "1..2000";
	                            }
	                            units milliseconds;
	                            mandatory true;
	                            description "The interval between CMTS transmission of successive Upstream Channel Descriptor messages for each upstream channel at this interface.";
	                            reference "RFC 4546";
	                        }
	                        leaf invited-ranging-attempts {
	                            type uint16 {
	                                range "0..1024";
	                            }
	                            units attempts;
	                            mandatory true;
	                            description "The maximum number of attempts to make on invitations for ranging requests.  A value of zero means the system SHOULD attempt to range forever.";
	                            reference "RFC 4546";
	                        }
	                        leaf im-insertion-interval {
	                            type uint32 {
	                                range "0..2147483647";
	                            }
	                            units HundredOfSeconds;
	                            mandatory true;
	                            description "The amount of time to elapse between each broadcast initial maintenance grant.  Broadcast initial maintenance grants are used to allow new cable modems to join the network.  Zero indicates that a vendor-specific algorithm  is used instead of a fixed time.  The maximum amount of time permitted by the specification is 2 seconds.";
	                            reference "RFC 4546";
	                        }
	                        leaf docsis11-concatenation-enabled {
	                            type boolean;
	                            default true;
	                            description "Enables and disables DOCSIS 1.1 concatenation.";
	                        }
	                        leaf docsis11-fragmentation-enabled {
	                            type boolean;
	                            default true;
	                            description "Enables and disables DOCSIS 1.1 fragmentation.";
	                        }
	                        container yang-ext5 {
	                            ccap:extensionPoint; //different pyang flags impact use of this hint
	                            description "node for vendor YANG extensions";
	                        }
	                    }
                    }
                    list upstream-physical-channel-ref {
                        key "slot us-rf-port upstream-physical-channel";
                        min-elements 0;
                        description "A reference to an upstream physical channel.";
                        uses upstream-physical-channel-reference;
                        container yang-ext {
                            ccap:extensionPoint; //different pyang flags impact use of this hint
                            description "node for vendor YANG extensions";
                        }
                    }
                    list non-primary-capable-ds {
                        key "slot ds-rf-port down-channel";
                        min-elements 0;
                        description "A reference to a non-primary capable DOCSIS downstream channel.
                                     Some CCAP implementations may implement the association of non primary capable downstream channels with MAC domain indirectly, based on RF plant topology configuration. In such a case CCAP device may ignore configuration settings communicated through the label Non-PrimaryCapableDs";
                                     
                        uses docsis-down-channel-reference;
                        container yang-ext {
                            ccap:extensionPoint; //different pyang flags impact use of this hint
                            description "node for vendor YANG extensions";
                        }
                    }
                    list primary-capable-ds {
                        key "slot ds-rf-port down-channel";
                        min-elements 0;
                        description "A reference to a primary capable DOCSIS downstream channel.";
                        uses docsis-down-channel-reference;
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container docs-multicast-authorization {
                description "The docs-multicast-authorization group of configuration elements allows for the configuration of DOCSIS Multicast. They are based on the configuration elements from [OSSIv3.0]. ";
                container control {
                    description "This object defines the CCAP global behavior for Multicast Authorization. Some parameters are included as part of the CM configuration process. In absence of those parameters, default values defined by attributes of this object are used.

";
                    reference 
                        "DOCSIS 3.0 Operations Support System Interface Specification
                         CM-SP-OSSIv3.0-I15-110623 Ctrl Object section.";
                    leaf enable {
                        type enable-type;
                        default disable;
                        description "This attribute enables the enforcement of Multicast Authorization feature.";
                    }
                    leaf default-profile-name-list {
                        type snmp-tag-list-type;
                        default " ";
                        description "This attribute indicates one or more Multicast Authorization Profiles that are used by the CMTS when CMs register with no Multicast Join Authorization encodings in the REG-REQ-(MP). When IP Multicast Authorization is enforced, this attribute provides the default set of Multicast Authorization Profiles the CMTS enforces for a CM in case the CM did not signal a set of profiles during the registration process. If the Default Multicast Authorization Group Name is a -zero-length string, the DefAction attribute determines whether a join request is authorized. If the CMTS supports more than one profile name as a default, the CMTS enforces each of the profiles in order of occurrence until the maximum number of profiles is reached.";
                    }
                    leaf default-action {
                        type authorization-action-type;
                        default deny;
                        description "This attribute defines the default authorization action when no IP Multicast Session Rule is determined to match a client's IP multicast JOIN request.";
                    }
                    leaf default-max-number-sessions {
                        type uint16;
                        default 0;
                        description "This attribute indicates the default maximum number of multicast sessions that clients reached through a particular CM are allowed to join. A DefMaxNumSess value of 0 indicates that no dynamic joins are permitted. A Maximum Multicast Sessions Encoding value of 65535 (the largest valid value) indicates that the CMTS permits any number of sessions to be joined by clients reached through the CM.
";
                        reference 
                            "DOCSIS 3.0 MAC and Upper Layer Protocols Interface Specification 
                             CM-SP-MULPIv3.0-I16-110623 Maximum Multicast Sessions section.";
                    }
                    container yang-ext {
                        ccap:extensionPoint; //different pyang flags impact use of this hint
                        description "node for vendor YANG extensions";
                    }
                }
                list profiles {
                    key mcast-auth-profile-name;
                    min-elements 0;
                    description 
                        "This object contains the description of the Multicast Authorization profiles for administrative purposes. 
                         This object supports the creation and deletion of multiple instances.
                         Creation of a new instance of this object requires the Description attribute to be set.";
                    reference 
                        "DOCSIS 3.0 Operations Support System Interface Specification
                         CM-SP-OSSIv3.0-I15-110623 Profiles Object section.";
                    leaf mcast-auth-profile-name {
                        type string {
                            length "1..15";
                        }
                        description "This attribute is a unique name or identifier for a Multicast Authorization Profile.";
                    }
                    leaf description {
                        type string;
                        mandatory true;
                        description "This attribute is a human readable description of the Multicast Authorization Profile.";
                    }
                    list session-rule {
                        key "id session-rule-name";
                        min-elements 1;
                        description 
                            "This object defines Operator configured profiles to be matched during the authorization process. 
                             This object supports the creation and deletion of multiple instances.
                             Creation of a new instance of this object requires the following attributes to be set:
                             - SrcPrefixAddr
                             - GrpPrefixAddr";
                        reference 
                            "DOCSIS 3.0 Operations Support System Interface Specification
                             CM-SP-OSSIv3.0-I15-110623 ProfileSessRule Object section.";
                        leaf session-rule-name {
                            type string {
                                length "1..15";
                            }
                            description "This attribute is a unique name that associates the IP Multicast Authorization Profile Name Subtype encoding signaled by CMs with the a set of Multicast Authorization Profile Session Rules.";
                        }
                        leaf id {
                            type uint32;
                            description "This attribute provides a unique identifier for each CMTS configured Multicast Authorization Profile Session rule within a Multicast Authorization Profile Name.";
                        }
                        leaf priority {
                            type uint32;
                            default 0;
                            description "This attribute configures the rule priority for the static session rule. Higher values indicate a higher priority. If more than one session rule matches a joined session, the session rule with the highest rule priority determines the authorization action.";
                        }
                        uses ssm-group;
                        leaf authorization-action {
                            type authorization-action-type;
                            default deny;
                            description 
                                "This attribute specifies the authorization action for a session join attempt that matches the session rule.";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            choice docsis-if {
	            case docs-if {
	                description "The docs-if object is the container for DOCSIS interface configuration objects.";
	                list modulation-profile {
	                    key modulation-index;
	                    min-elements 1;
	                    description "This object is based on the docsIfCmtsModulationTable defined in [RFC 4546].";
	                    reference "RFC 4546";
	                    leaf modulation-index {
	                        type uint32 {
	                            range "1..2147483647";
	                        }
	                        description "An index into the Channel Modulation table representing a group of Interval Usage Codes, all associated with the same channel.";
	                    }
	                    list interval-usage-code {
	                        key usage-code;
	                        min-elements 1;
	                        max-elements 14;
	                        description "This object allows a list of interval usage codes to be associated with a single modulation profile. It is based on the docsIfCmtsModulationTable defined in [RFC 4546].
	                             Reference: [RFC 4546] docsIfCmtsModulationTable.";
	                        leaf usage-code {
	                            type modulation-interval-usage-code-type;
	                            mandatory true;
	                            description "An index into the Channel Modulation table that, when grouped with other Interval Usage Codes, fully instantiates all modulation sets for a given upstream channel.";
	                        }
	                        leaf modulation {
	                            type modulation-type;
	                            default qpsk;
	                            description "The modulation type used on this channel.";
	                        }
	                        leaf preamble-length {
	                            type preamble-length-type;
	                            mandatory true;
	                            description "The preamble length for this modulation profile in bits.";
	                        }
	                        leaf differential-encoding {
	                            type boolean;
	                            default false;
	                            description "Specifies whether or not differential encoding is used on this channel.";
	                        }
	                        leaf fec-error-correction {
	                            type fec-error-correction-type;
	                            default 0;
	                            description "The number of correctable errored bytes (t) used in forward error correction code.";
	                        }
	                        leaf fec-codeword-length {
	                            type fec-codeword-length-type;
	                            default 32;
	                            description 
	                                "The number of data bytes (k) in the forward error correction codeword.
	                                 This object is not used if fec-error-correction is zero.";
	                        }
	                        leaf scrambler-seed {
	                            type scrambler-seed-type;
	                            default 0;
	                            description "The 15-bit seed value for the scrambler polynomial.";
	                        }
	                        leaf max-burst-size {
	                            type uint8;
	                            units mini-slots;
	                            mandatory true;
	                            description "The maximum number of mini-slots that can be transmitted during this channel's burst time. Default value is 0, except for shortData, where it is 8.";
	                        }
	                        leaf last-codeword-shortened {
	                            type boolean;
	                            default true;
	                            description "Indicates whether the last FEC codeword is truncated.";
	                        }
	                        leaf scrambler {
	                            type boolean;
	                            default false;
	                            description "Indicates whether the scrambler is employed.";
	                        }
	                        leaf byte-interleaver-depth {
	                            type uint32;
	                            default 1;
	                            description "ATDMA Byte Interleaver Depth (Ir).";
	                        }
	                        leaf byte-interleaver-block-size {
	                            type uint32;
	                            default 18;
	                            description "ATDMA Byte Interleaver Block size (Br).";
	                        }
	                        leaf preamble {
	                            type preamble-type;
	                            default qpsk0;
	                            description "Preamble type for DOCSIS 2.0 bursts.  ";
	                        }
	                        leaf tcm-error-correction-on {
	                            type boolean;
	                            default false;
	                            description "Trellis Code Modulation (TCM) On/Off.";
	                        }
	                        leaf scdma-interleaver-step-size {
	                            type scdma-interleaver-step-size-type;
	                            default 1;
	                            description "S-CDMA Interleaver step size.";
	                        }
	                        leaf scdma-spreader-enable {
	                            type boolean;
	                            description "S-CDMA spreader.  Default value for IUC 3 and 4 is OFF; for all other IUCs it is ON.";
	                        }
	                        leaf scdma-subframe-codes {
	                            type scdma-subframe-codes-type;
	                            default 1;
	                            description "S-CDMA sub-frame size.";
	                        }
	                        leaf channel-type {
	                            type us-channel-type;
	                            default tdma;
	                            description "Describes the modulation channel type for this modulation entry.";
	                        }
	                        container yang-ext {
	                            ccap:extensionPoint; //different pyang flags impact use of this hint
	                            description "node for vendor YANG extensions";
	                        }
	                    }
	                    container yang-ext {
	                        ccap:extensionPoint; //different pyang flags impact use of this hint
	                        description "node for vendor YANG extensions";
	                    }
	                }
	                container yang-ext6 {
	                    ccap:extensionPoint; //different pyang flags impact use of this hint
	                    description "node for vendor YANG extensions";
	                }
	            }
            }
            container docs-packet-cable {
                description "The docs-packet-cable object is the container for PacketCable configuration objects.";
                choice packet-cable {
	                case packet-cable-config {
	                    description "This object is used for configuring PacketCable and PCMM services on the CCAP.";
	                    leaf packet-cable-enabled {
	                        type boolean;
	                        default false;
	                        description "This configuration attribute allows the operator to enable PacketCable services on the CCAP.";
	                    }
	                    leaf pcmm-enabled {
	                        type boolean;
	                        default false;
	                        description "This configuration attribute allows the operator to enable PacketCable Multimedia services on the CCAP.";
	                    }
	                    leaf pc-t0-timer {
	                        type uint8;
	                        units seconds;
	                        default 30;
	                        description "This configuration attribute allows the operator to define the value in seconds for the PacketCable T0 timer.";
	                    }
	                    leaf pc-t1-timer {
	                        type uint32;
	                        units seconds;
	                        default 200;
	                        description "This configuration attribute allows the operator to define the value in seconds for the PacketCable T1 timer.";
	                    }
	                    leaf pc-t7-timer {
	                        type uint32;
	                        units seconds;
	                        default 200;
	                        description 
	                            "This attribute allows for the setting of the Timeout for Admitted QoS Parameters for the service flow to the value specified for this timer. In the case of a flow with multiple sub-flows, the flow's Timeout for Admitted QoS
	                             Parameters is set to the value of timer T7 from the most recently received Gate-Set message for any subflow on the flow. The Timeout for Admitted QoS Parameters limits the period of time that the CMTS holds resources for a service flow's Admitted QoS Parameter Set while they are in excess of its Active QoS Parameter Set. ";
	                        reference "PacketCable 1.5 Dynamic Quality-of-Service Specification, PKT-SP-DQOS1.5-I04-090624";
	                    }
	                    leaf pc-t8-timer {
	                        type uint8;
	                        units seconds;
	                        default 0;
	                        description "This attribute configures the Timeout for Active QoS Parameters for the service flow to the value specified in for this timer. In the case of a flow with multiple sub-flows, the flow's Timeout for Active QoS Parameters is set to the value of timer T8 from the most recently received Gate-Set message for any sub-flow on the flow. The Timeout for Active QoS Parameters limits the period of time resources remain unused on an active service flow. 
	";
	                        reference "PacketCable 1.5 Dynamic Quality-of-Service Specification, PKT-SP-DQOS1.5-I04-090624";
	                    }
	                    leaf pcmm-t1-timer {
	                        type uint8;
	                        units seconds;
	                        default 200;
	                        description "This configuration attribute allows the operator to define the value in seconds for the PacketCable Multimedia T1 timer.";
	                    }
	                    leaf cmts-gate-id-value {
	                        type uint32 {
	                            range "0..16383";
	                        }
	                        mandatory true;
	                        description "This configuration attribute allows the operator to define the value for the CMTS Id portion of PCMM GateIds.";
	                    }
	                    leaf tos {
	                        type int8 {
	                            range "-1 | 0..63";
	                        }
	                        mandatory true;
	                        description "This configuration attribute allows the operator to define the value for the Tos bits in outgoing COPS messages.";
	                    }
	                    leaf cops-connection-threshold {
	                        type uint32;
	                        units "connections/15 mins";
	                        mandatory true;
	                        description "This configuration attribute allows the operator to define the threshold number of COPS connections per 15 minute interval.";
	                    }
	                    leaf control-point-discovery-enabled {
	                        type boolean;
	                        default false;
	                        description "This attribute enables or disables the Control point Discovery functionality described in the PacketCable Specifications.";
	                    }
	                    container yang-ext7 {
	                        ccap:extensionPoint; //different pyang flags impact use of this hint
	                        description "node for vendor YANG extensions";
	                    }
	                }
                }
                choice pc-event {
	                case pc-event-config {
	                    description "This object configures event messaging for PacketCable.";
	                    leaf retry-timer {
	                        type uint16 {
	                            range "10..10000";
	                        }
	                        units milliseconds;
	                        default 3000;
	                        description "This configuration attribute allows the configuration of the number of milli-seconds the CCAP should wait before sending a message that was not acknowledged.";
	                    }
	                    leaf retry-limit {
	                        type uint8 {
	                            range "0..9";
	                        }
	                        default 3;
	                        description "This configuration attribute allows the configuration of the number of times the CCAP should retry when sending a message.";
	                    }
	                    leaf batch-size {
	                        type uint32;
	                        mandatory true;
	                        description "This configuration attribute allows the configuration of the number of records the CCAP should bundle in a single message to a billing or Record Keeping Server (RKS).";
	                    }
	                    leaf max-age {
	                        type uint32;
	                        units seconds;
	                        mandatory true;
	                        description "This object defines the max age of messages to be sent to a RKS or billing server.";
	                    }
	                    leaf billing-events {
	                        type boolean;
	                        default false;
	                        description "This attribute tells the CCAP if it needs to send billing events to a billing server/RKS.";
	                    }
	                    container yang-ext8 {
	                        ccap:extensionPoint; //different pyang flags impact use of this hint
	                        description "node for vendor YANG extensions";
	                    }
	                }
	                container yang-ext {
	                    ccap:extensionPoint; //different pyang flags impact use of this hint
	                    description "node for vendor YANG extensions";
	                }
	
	            }
            }
            container docs-dsg {
                description "The docs-dsg object is the container for DSG configuration objects.";
                list dsg-timer-config {
                    key timer-config-index;
                    min-elements 0;
                    description 
                        "This configuration object is based on the dsgIfTimerTable defined in [DSG] and will be used with modifications for CCAP.
                         The DSG Timer Table contains timers that are sent to the DSG client(s) via the DCD message. ";
                    reference 
                        "DOCSIS Set-top Gateway (DSG) Interface Specification CM-SP-DSG-I18-110623
                         DOCSIS Set-top Gateway Agent MIB Definition section";
                    leaf timer-config-index {
                        type uint32 {
                            range "1..4294967295";
                        }
                        description "The index for timer-config list.";
                    }
                    leaf init-t-dsg-1 {
                        type uint16 {
                            range "1..65535";
                        }
                        units seconds;
                        default 2;
                        description "Initialization Timeout. This is the timeout period in seconds for the DSG packets during initialization of the DSG client.";
                    }
                    leaf oper-t-dsg-2 {
                        type uint16 {
                            range "1..65535";
                        }
                        units seconds;
                        default 600;
                        description "Operational Timeout. This is the timeout period in seconds for the DSG packets during normal operation of the DSG client.";
                    }
                    leaf two-way-t-dsg-3 {
                        type uint16;
                        units seconds;
                        default 300;
                        description "Two-way retry timer. This is the retry timer that determines when the DSG client attempts to reconnect with the DSG Agent and established two-way connectivity. Default value is 300 seconds. The value 0 indicates that the client will continuously retry two-way operation";
                    }
                    leaf one-way-t-dsg-4 {
                        type uint16;
                        units seconds;
                        default 1800;
                        description "One-way retry timer. The retry timer that determines when the client attempts to rescan for a DOCSIS downstream channel that contains DSG packets after a TimerTdsg1 or TimerTdsg2 timeout. Default value is 1800 seconds. The value 0 indicates that the client will immediately begin scanning upon TimerTdsg1 or TimerTdsg2 timeout.";
                    }
                    container yang-ext {
                        ccap:extensionPoint; //different pyang flags impact use of this hint
                        description "node for vendor YANG extensions";
                    }
                }
                list dsg-downstream {
                    key dsg-downstream-index;
                    min-elements 0;
                    description "The dsg-downstream object represents an individual downstream channel for DSG configuration purposes. This configuration object is based on the dsgIfDownstreamTable defined in [DSG] and will be used with modifications for CCAP.";
                    leaf dsg-downstream-index {
                        type uint32;
                        description "This is the key for an instance of this object. In [DSG], this was the channel ifIndex. Here, the channel is identified uniquely by the docsis-down-channel-ref.";
                    }
                    leaf enable-dcd {
                        type boolean;
                        mandatory true;
                        description "This attribute is used to enable or disable DCD messages to be sent on this downstream channel. The value is always true for those downstreams that contain DSG tunnels.";
                    }
                    container docsis-down-channel-ref {
                        description "This is a reference to a DOCSIS down channel instance.";
                        ccap:inlineType;
                        uses docsis-down-channel-reference;
                        container yang-ext {
                            ccap:extensionPoint; //different pyang flags impact use of this hint
                            description "node for vendor YANG extensions";
                        }
                    }
                    leaf timer-config-index {
                        type leafref {
                            path "../../dsg-timer-config/timer-config-index";
                        }
                        description "Reference to the timer-config index. Zero means not configured.";
                    }
                    leaf vendor-param-id {
                        type leafref {
                            path "../../vendor-parameters-list/vendor-param-id";
                        }
                        description "Reference to the vendor-parameters id. Zero means not configured.";
                    }
                    leaf dsg-channel-list-index {
                        type leafref {
                            path "../../dsg-channel-list/dsg-channel-list-index";
                        }
                        description "Reference to dsg-channel-list enumerating the frequencies carrying DSG tunnels. Zero means not configured.";
                    }
                    container yang-ext {
                        ccap:extensionPoint; //different pyang flags impact use of this hint
                        description "node for vendor YANG extensions";
                    }
                }
                list dsg-channel-list {
                    key "dsg-channel-list-index";
                    min-elements 0;
                    description 
                        "This configuration object is based on the dsgIfChannelListTable defined in [DSG] and will be used with modifications for CCAP.
                         The DownChanList object allows for configuration of a list of one or multiple downstream frequencies that are carrying DSG tunnel(s). This configuration object has been modified from the DSG Specification definitions.";
                    reference 
                        "DOCSIS Set-top Gateway (DSG) Interface Specification CM-SP-DSG-I18-110623
                         DOCSIS Set-top Gateway Agent MIB Definition section";
                    leaf dsg-channel-list-index {
                        type uint32 {
                            range "1..4294967295";
                        }
                        description "The index of the dsg channel list.";
                    }
                    list dsg-channel {
                        key "dsg-channel-index";
                        min-elements 1;
                        description "The frequencies carrying DSG tunnels for some RF connector.";
                        leaf dsg-channel-index {
                            type uint32;
                            description "The local index of the channel.";
                        }
                        leaf channel-downstream-frequency {
                            type uint32 {
                                range "0..1000000000";
                            }
                            units Hz;
                            default 0;
                            description "The channel-downstream-frequency attribute represent a frequency of a downstream channel carrying DSG information. Frequency is a multiple of 62500 Hz, per [DSG]";
                            reference 
                                "DOCSIS Set-top Gateway (DSG) Interface Specification CM-SP-DSG-I18-110623
                                 DOCSIS Set-top Gateway Agent MIB Definition section";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                list tunnel-group-to-channel-list {
                    key "tunnel-group-index";
                    min-elements 0;
                    description 
                        "This configuration object is based on the dsgIfTunnelGrpToChannelTable defined in [DSG] and will be used with modifications for CCAP.
                         The TunnelGrpToChannel object permits association of a group of tunnels to one or more downstream channels. This configuration object has been modified from the DSG Specification definitions.";
                    reference 
                        "DOCSIS Set-top Gateway (DSG) Interface Specification CM-SP-DSG-I18-110623
                         DOCSIS Set-top Gateway Agent MIB Definition section";
                    leaf tunnel-group-index {
                        type uint32;
                        description "This attribute is the key for this tunnel group.";
                    }
                    list tunnel-group-channel {
                        key "tunnel-group-channel-index";
                        min-elements 1;
                        description "The channels in the tunnel group and the tunnel group parameters for each channel.";
                        leaf tunnel-group-channel-index {
                            type uint32;
                            description "This attribute configures the linkage to a specific DownChan instance that will carry the DSG tunnels in this tunnel group.";
                        }
                        leaf rule-priority {
                            type uint8 {
                                range "0..255";
                            }
                            default 0;
                            description "The DSG rule priority determines the order in which the DSG rules are applied by the DSG client. The default value is 0, which is the lowest priority.";
                        }
                        leaf vendor-param-id {
                            type leafref {
                                path "../../../vendor-parameters-list/vendor-param-id";
                            }
                           description "Reference to the Vendor Parameters Id. Zero means not configured.";
                        }
                        leaf dsg-downstream-index {
                            type leafref {
                                path "../../../dsg-downstream/dsg-downstream-index";
                            }
                            mandatory true;
                            description "Reference to the DSG Down Channel Index.";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                list dsg-tunnel-config {
                    key dsg-tunnel-config-index;
                    min-elements 0;
                    description 
                        "A dsg-tunnel-config object allows the operator to configure DSG tunnels. Each DSG Tunnel represents a stream of packets delivered to a DSG Client in a set-top device and is configured with a single destination MAC address.
                         This configuration object is based on the dsgIfTunnelTable defined in [DSG] and is used with modifications.";
                    reference 
                        "DOCSIS Set-top Gateway (DSG) Interface Specification CM-SP-DSG-I18-110623
                         DOCSIS Set-top Gateway Agent MIB Definition section";
                    leaf dsg-tunnel-config-index {
                        type uint32;
                        description "This attribute is the index for a tunnel that could be associated to one or more downstream channel that carries DSG tunnels.";
                    }
                    leaf tunnel-grp-index {
                        type leafref {
                            path "../../tunnel-group-to-channel-list/tunnel-group-index";
                        }
                        description "Reference to the DSG tunnel-grp containing this tunnel.";
                    }
                    leaf mac-address {
                        type yang:mac-address;
                        mandatory true;
                        description "This attribute configures the DSG tunnel destination MAC address.";
                    }
                    leaf client-id-list-index {
                        type leafref {
                            path "../../client-id-config-list/client-id-list-index";
                        }
                        description "Reference to one or more objects in client-id-config. Zero means not configured.";
                    }
                    leaf service-class-name {
                        type leafref {
                            path "/ccap/docsis/docs-qos/service-class/service-class-name";
                        }
                        mandatory true;
                        description "Reference to a service-class name.";
                    }
                    container yang-ext {
                        ccap:extensionPoint; //different pyang flags impact use of this hint
                        description "node for vendor YANG extensions";
                    }
                }
                list dsg-classifier {
                    key dsg-classifier-id;
                    min-elements 0;
                    description "This configuration object is based on the dsgIfClassifierTable defined in [DSG] and will be used with modifications for CCAP.";
                    reference 
                        "DOCSIS Set-top Gateway (DSG) Interface Specification CM-SP-DSG-I18-110623
                         DOCSIS Set-top Gateway Agent MIB Definition section";
                    leaf dsg-classifier-id {
                        type uint16 {
                        range "1..65535";
                        }
                        description "This attribute configures the linkage between the DSG tunnel for which this classifier will apply.";
                    }
                    leaf tunnel-index {
                        type leafref {
                            path "../../dsg-tunnel-config/dsg-tunnel-config-index";
                        }
                        description "Reference to the DSG tunnel using this classifier.";
                    }
                    leaf priority {
                        type uint8;
                        default 0;
                        description "This attribute is used to configure the DSG rule priority that determines the order of which channel and its associated UCIDs should be applied by the DSG client. The default value is 0, which is the lowest priority.";
                    }
                    leaf source-ip {
                        type inet:ipv4-prefix;
                        mandatory true;
                        description "This attribute configures the source prefix for the DSG tunnel. Currently, the CCAP only supports IPv4 addresses for DSG tunnels, per [DSG]";
                        reference 
                            "DOCSIS Set-top Gateway (DSG) Interface Specification CM-SP-DSG-I18-110623
                             DOCSIS Set-top Gateway Agent MIB Definition section";
                    }
                    leaf destination-ip {
                        type inet:ipv4-address;
                        mandatory true;
                        description "This attribute configures the destination IP address for the DSG tunnel. Currently, the CCAP only supports Ipv4 addresses for DSG tunnels, per [DSG].";
                        reference 
                            "DOCSIS Set-top Gateway (DSG) Interface Specification CM-SP-DSG-I18-110623
                             DOCSIS Set-top Gateway Agent MIB Definition section";
                    }
                    leaf destination-port-start {
                        type inet:port-number;
                        default 0;
                        description "This attribute configures the inclusive lower bound of the transport-layer source port range that is to be matched.";
                    }
                    leaf destination-port-end {
                        type inet:port-number;
                        default 65535;
                        description "This attribute the inclusive higher bound of the transport-layer source port range that is to be matched.";
                    }
                    leaf include-in-dcd {
                        type boolean;
                        default true;
                        description "Indicates whether or not this DSG classifier will be sent in DCD messages for use as a Layer-3 and Layer-4 packet filter by the DSG eCM.";
                    }
                    container yang-ext {
                        ccap:extensionPoint; //different pyang flags impact use of this hint
                        description "node for vendor YANG extensions";
                    }
                }
                list vendor-parameters-list {
                    key "vendor-param-id";
                    min-elements 0;
                    description 
                        "This configuration object is based on the dsgIfVendorParamTable defined in [DSG] and will be used without modification for CCAP.
                         The DSG Vendor Parameter Table allows vendors to send specific parameters to the DSG clients within a DSG rule or within the DSG Configuration block in a DCD message.";
                    reference 
                        "DOCSIS Set-top Gateway (DSG) Interface Specification CM-SP-DSG-I18-110623
                         DOCSIS Set-top Gateway Agent MIB Definition section";
                    leaf vendor-param-id {
                        type uint32 {
                            range "1..4294967295";
                        }
                        description "This attribute represents a key to the vendor-parameters object. ";
                    }
                    list vendor-param {
                        key "vendor-index";
                        min-elements 1;
                        description "A single vendor parameter.";
                        leaf vendor-index {
                            type uint32;
                            description "The vendor-specific identifier configured for each instance of the pair of VendorOui and VendorValue attributes.";
                        }
                        leaf vendor-oui {
                            type ccap-octet-data-type {
                                length "6";
                            }
                            mandatory true;
                            description "The vendor-oui attribute allows for the configuration of vendor-assigned organization unique ID (OUI).";
                        }
                        leaf vendor-value {
                            type ccap-octet-data-type {
                                length "0..100";
                            }
                            mandatory true;
                            description "This attribute represents a vendor-specific parameter value in the form of an octet string.";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                list client-id-config-list {
                    key "client-id-list-index";
                    min-elements 0;
                    description 
                        "This configuration object is based on the dsgIfClientIdTable defined in [DSG] and will be used with modifications for CCAP.
                         The Client Identification object contains the client identification type and value. It also contains the vendor-specific parameter identification. There could be multiple client ids associated to a tunnel, grouped by the ListIndex.";
                    reference 
                        "DOCSIS Set-top Gateway (DSG) Interface Specification CM-SP-DSG-I18-110623
                         DOCSIS Set-top Gateway Agent MIB Definition section";
                    leaf client-id-list-index {
                        type uint32 {
                            range "1..4294967295";
                        }
                        description "This attribute identifies a specific DSG client list.";
                    }
                    list dsg-client {
                        key "client-id-index";
                        min-elements 1;
                        description "A single DSG client.";
                        leaf client-id-index {
                            type uint32;
                            description "This attribute identifies a single client on a DSG client list.";
                        }
                        leaf dsg-client-id-type {
                            type dsg-client-id-class-type;
                            default broadcast;
                            description "The Client Identification type.";
                        }
                        leaf client-id-value {
                            type ccap-octet-data-type {
                                length "12";
                            }
                            default 000000000000;
                            description "The Client Identification Value. The content depends on the value of the dsgIfClientIdType. For dsgIfClientIdType of a type broadcast(1), this object will have a 16-bit value whether or not it is a length 0 or length 2 broadcast ID. If the value is 0, then the encoded Type Length Value Attribute (TLV) in the DCD would be the original, zero length, broadcast ID. If the value is specified in Table 5-2 of [DSG], then the TLV in the DCD would be a length 2 broadcast ID followed by the value. For ClientIdType of a type macAddress(2), this object is a well-known MAC address. For ClientIdType of a type caSystemId(3), this object is a CA System ID. For ClientIdType of a type applicationId(4), this object is an application ID. Client IDs representing types broadcast(1), caSystemId(3) or applicationId(4) are encoded in DCD messages as Unsigned integers and configured in this object as 6 octet string with the 2 LSB for the client ID value, e.g., an applicationId 2048 (0x0800) is encoded as '000000000800'h.";
                        }
                        leaf vendor-parameters-id {
                            type leafref {
                                path "../../../vendor-parameters-list/vendor-param-id";
                            }
                            description "Reference to Vendor Parameters Id.";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container docs-load-balancing {
                leaf enable {
                    type boolean;
                    default false;
                }
                container general-grp-defaults {
                    description "This object provides the default load balancing parameters for General Load
                           Balancing Groups (MD-CM-SGs) that are used when instances of GeneralGrpCfg are
                           created by the CMTS.";
                    leaf enable {
                        type boolean;
                    }
                    leaf policy-id {
                        type leafref {
                            path "../../load-balancing-policy/policy-id";
                        }
                    }
                    leaf init-tech {
                        type load-bal-init-tech-type;
                        default "reinit-mac broadcast-ranging unicast-ranging ranging direct";
                    }
                    container yang-ext {
                        ccap:extensionPoint; //different pyang flags impact use of this hint
                        description "node for vendor YANG extensions";
                    }
                }
                list load-balancing-policy {
                    key policy-id;
                    description "This object describes the set of load balancing policies. Instances from
                            this object might be referenced by GrpStatus object . All the rules contained
                            in a load balancing policy apply to an Autonomous Load Balancing operations.
                            Load balancing rules are defined within this specification or can be
                            vendor-defined as well.";
                    leaf policy-id {
                        type uint32;
                    }
                    list load-balance-rule {
                        key rule-id;
                        min-elements 1;
                        leaf rule-id {
                            type leafref {
                                path "../../../basic-rule/rule-id";
                            }
                        }
                    }
                    container yang-ext {
                        ccap:extensionPoint; //different pyang flags impact use of this hint
                        description "node for vendor YANG extensions";
                    }
                }
                list basic-rule {
                    key rule-id;
                    description "This object represents a basic ruleset applicable to a load balancing
                          policy that references it.";
                    leaf rule-id {
                        type uint32;
                    }
                    leaf enable {
                        type load-balancing-rule-type;
                        description "This attribute when set to 'enabled' enables Autonomous Load
                               Balancing (independently of the load balancing group enable/disable state),
                               the rule set is disabled if set to 'disabled', or is disabled during a
                               period of time it set to 'disabledPeriod'.";
                    }
                    leaf disable-start {
                        type uint32 {
                            range "0..86399";
                        }
                        description "This attribute disables load balancing from the time stated by this
                               attribute when the attribute Enable is set to 'disablePeriod'. The time is
                               defined in seconds since midnight.";
                    }
                    leaf disable-end {
                        type uint32 {
                            range "1..86400";
                        }
                        description "This attribute disables load balancing until the time stated by this
                               attribute when the attribute Enable is set to 'disabled-period'. The time is
                               defined in seconds of the wall clock since midnight. Must be greater than
                               disable-start.";
                    }
                    container yang-ext {
                        ccap:extensionPoint; //different pyang flags impact use of this hint
                        description "node for vendor YANG extensions";
                    }
                }
                list general-grp-cfg {
                    key "mac-domain-name";
                    description "This object provides the parameters for the General Load Balancing Groups
                          of MD-CM-SGs associated with MAC Domain-Fiber Node pairs. This object allows
                          configuration of load balancing parameters for General Load Balancing Groups by
                          way of MAC Domain-Fiber Node pairs.  In many deployments, a MAC Domain-Fiber Node
                          pair will equate to an MD-CM-SG (which always equates to a GLBG).  In the case
                          where an MD-CM-SG spans multiple Fiber Nodes, there will be multiple elements in
                          the fiber node list.";
                    leaf mac-domain-name {
                        type leafref {
                            path "/ccap/docsis/docs-mac-domain/mac-domain/mac-domain-name";
                        }
                    }
                    list fiber-node {
                        key "fiber-node-index";
                        min-elements 1;
	                    leaf fiber-node-index {
	                        type leafref {
	                            path "/ccap/chassis/fiber-node-config/fiber-node-config-index";
	                        }
	                    }
	                    container yang-ext {
	                        ccap:extensionPoint; //different pyang flags impact use of this hint
	                        description "node for vendor YANG extensions";
	                    }
                    }
                    leaf policy-id {
                        type leafref {
                            path "../../load-balancing-policy/policy-id";
                        }
                        mandatory true;
                    }
                    leaf enable {
                        type boolean;
                        default true;
                    }
                    leaf init-tech {
                        type load-bal-init-tech-type;
                        default "";
                    }
                    container yang-ext {
                        ccap:extensionPoint; //different pyang flags impact use of this hint
                        description "node for vendor YANG extensions";
                    }
                }
                list restricted-grp-cfg {
                    key res-grp-id;
                    description "This object represents the configuration of Restricted Load Balancing Groups.";
                    leaf res-grp-id {
                        type uint32;
                    }
                    list grp-mac-domain {
                        key mac-domain-name;
                        min-elements 1;
                        leaf mac-domain-name {
                            type leafref {
                                path "/ccap/docsis/docs-mac-domain/mac-domain/mac-domain-name";
                            }
                            description "This attribute represents one or more MAC domain where the Restricted Load
                                  balancing Group applies. Vendors are only required to support one MAC Domain.";
                        }
                    }
                    leaf init-tech {
                        type load-bal-init-tech-type;
                    }
                    leaf policy-id {
                        type leafref {
                            path "../../load-balancing-policy/policy-id";
                        }
                    }
                    leaf service-type-id-list {
                        type snmp-tag-list-type;
                        description "This attribute represents the Service Type Id associated
                                     with this cable modem MAC address - MAC Address
                                     mask combination.. The zero-length string indicates
                                     that the instance is matched only against the GrpId
                                     value, if both GrpId and this attribute are not present
                                     the instance is ignored for matching purposes.";
                    }
                    list upstream-logical-channel-ref {
                        key "slot us-rf-port upstream-physical-channel upstream-logical-channel";
                        min-elements 0;
                        description "This element configures one or more upstream logical channel to be
                                part of this restricted load-balancing group.";
                        uses upstream-logical-channel-reference;
                        container yang-ext {
                            ccap:extensionPoint; //different pyang flags impact use of this hint
                            description "node for vendor YANG extensions";
                        }
                    }
                    list docsis-down-channel-ref {
                        key "slot ds-rf-port down-channel";
                        description "A reference to a DOCSIS downstream channel.";
                        ccap:inlineType;
                        uses docsis-down-channel-reference;
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                list restrict-cm-cfg {
                    key restricted-cm-id;
                    description "This object describes the list of cable modems being statically provisioned
                                 at the CMTS to a Restricted Load Balancing Group.";
                    leaf restricted-cm-id {
                        type uint32;
                    }
                    leaf mac-addr {
                        type yang:mac-address;
                        default 00:00:00:00:00:00;
                    }
                    leaf mac-mask {
                        type yang:mac-address;
                        default FF:FF:FF:FF:FF:FF;
                    }
                    leaf service-type-id {
                        type string {
                            length "0..16";
                        }
                    }
                    leaf restricted-grp-id {
                        type leafref {
                            path "../../restricted-grp-cfg/res-grp-id";
                        }
                        description "The attribute represents the Restricted Load Balancing Group identifier
                                of this entry associated with the cable modem MAC address - MAC address mask
                                combination. If not present, then the instance is matched only
                                against the ServiceTypeId value.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            list ofdma-profile {
                key ofdma-profile-index;
                description "The list of profiles for OFDMA channels. Must have at least one if a OFDMA channel is defined.";
                leaf ofdma-profile-index {
                    type uint8;
                    description "";
                }
                leaf ofdma-profile-name {
                    type string {
                        length "10..32";
                    }
                    mandatory true;
                    description "This attribute contains the name of this OFDMA modulation profile";
                }
                leaf ofdma-profile-description {
                    type string {
                        length "0..255";
                    }
                    description "This attribute contains a description of this OFDMA modulation profile";
                }
                leaf subcarrier-spacing {
                    type subcarrier-spacing-type;
                    mandatory true;
                    description "This attribute defines the subcarrier spacing and therefore the FFT mode (2k or 4k) for the channel.";
                }
                leaf ofdma-cyclic-prefix {
                    type ofdma-cyclic-prefix-type;
                    mandatory true;
                    description "This data type is defined to specify the allowed values for applying cyclic prefix for mitigating interference due to microreflections.";
                }
                leaf roll-off-period {
                    type ofdma-windowing-type;
                    mandatory true;
                    description "This data type is defined to specify the allowed values for applying windowing to maximize the capacity of the upstream channel.";
                }
                leaf symbols-per-frame {
                    type uint8 {
                        range "1 | 6..36";
                    }
                    mandatory true;
                    description "The number of symbols per minislot is this value times 8, for 2k FFT mode, or this value times 16, for 4k FFT mode.";
                }
                leaf pre-eq-enable {
                    type boolean;
                    mandatory true;
                    description "This attribute enables pre-equalization on the OFDMA upstream Channel when its value is true, or disables pre-equalization when its value is false.";
                }
                container initial-ranging-iuc {
                    uses ofdma-ranging-group;
                    leaf num-subcarriers {
                        type uint16 {
                            range "16..128";
                        }
                        mandatory true;
                        description "This attribute defines maximum number of subcarriers for initial ranging. This is the maximum number of subcarriers for initial ranging, not including the guardband. This value is limited to 64 subcarriers with 50 kHz subcarrier spacing and 128 subcarriers with 25 kHz subcarrier spacing ([PHY3.1], section 7.4.2.16.6). ";
                    }
                    leaf num-admission-slots {
                        type uint8 {
                            range "1..8";
                        }
                        mandatory true;
                        description "This attribute defines the number of preamble symbols before duplication used for initial ranging ([PHY3.1], section 7.4.2.16.6).";
                    }
                    container yang-ext {
                        ccap:extensionPoint; //different pyang flags impact use of this hint
                        description "node for vendor YANG extensions";
                    }
                }
                container fine-ranging-iuc {
                    uses ofdma-ranging-group;
                    leaf num-subcarriers {
                        type uint16 {
                            range "16..512";
                        }
                        mandatory true;
                        description "This attribute defines maximum number of subcarriers for fine ranging. The following rules apply ([PHY3.1], section 7.4.2.16.6):
                             1. The maximum number of subcarriers for fine ranging, not including the guardband but including subcarriers in the exclusion zones MUST NOT exceed 512 subcarriers.
                             2.Maximum number of subcarriers for fine ranging, not including the guardband and not including exclusions MUST NOT exceed 256 subcarriers with 50 kHz subcarrier spacing and 512 subcarriers with 25 kHz subcarrier spacing. Note that if 512 subcarriers are used there cannot be exclusion bands within the fine ranging signal to comply with the previous requirement.";
                    }
                    container yang-ext {
                        ccap:extensionPoint; //different pyang flags impact use of this hint
                        description "node for vendor YANG extensions";
                    }
                }
                list data-iuc {
                    key data-iuc-index;
                    min-elements 1;
                    max-elements 7;
                    leaf data-iuc-index {
                        type uint8 {
                            range "5|6|9..13";
                        }
                        description "Data IUC number";
                    }
                    leaf def-modulation {
                        type ofdma-modulation-type;
                        mandatory true;
                        description "This attribute is the default modulation for the minislots in this US OFDMA channel.";
                    }
                    leaf def-pilot-pattern {
                        type uint8 {
                            range "1..14";
                        }
                        mandatory true;
                        description "This attribute is default pilot pattern for the minislots in this US OFDMA channel. Channels using 2k mode are restricted to patterns 1-7, while channels using 4k mode are restricted to patterns 8-14 ([PHY3.1], section 7.4.16.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
        container video {
            description "The video object is the primary container of video configuration objects.";
            reference 
                "CCAP Operations Support System Interface Specification
                 CM-SP-CCAP-OSSI-I01-110930 CCAP Video Session Configuration Objects section.";
            container global-input-ts-config {
                description "This object represents the global configuration of input transport streams.";
                leaf jitter-tolerance {
                    type uint32;
                    units milliseconds;
                    default 100;
                    description "This attribute represents the acceptable delay variation in millisecond for incoming streams. The jitter option sets the size of a dejittering buffer that absorbs the input jitter of a session.";
                }
                leaf unicast-session-loss-timeout {
                    type uint32;
                    units milliseconds;
                    default 5000;
                    description "This attribute represents the loss of signal timeout in milliseconds for unicast input streams. ";
                    reference "ANSI SCTE 154-4 2008, MPEG Management Information Base SCTE-HMS-MPEG-MIB mpegLossOfSignalTimeout.";
                }
                leaf multicast-session-loss-timeout {
                    type uint32;
                    units milliseconds;
                    default 5000;
                    description "This attribute represents the loss of signal timeout in milliseconds for the multicast input streams.";
                }
                container yang-ext {
                    ccap:extensionPoint; //different pyang flags impact use of this hint
                    description "node for vendor YANG extensions";
                }
            }
            container global-output-ts-config {
                description "This object represents the global configuration of output transport streams.";
                leaf cat-insert-rate {
                    type uint8 {
                        range "0..32";
                    }
                    units "tables per second";
                    default 10;
                    description "This attribute represents the CAT insertion rate expressed in tables/second.";
                    reference "ANSI SCTE 154-4 2008, MPEG Management Information Base SCTE-HMS-MPEG-MIB mpegOutputTSCatInsertRate";
                }
                leaf pat-insert-rate {
                    type uint8 {
                        range "0..32";
                    }
                    units "tables per second";
                    default 10;
                    description "This attribute represents the PAT table interval expressed in tables/second.";
                    reference "ANSI SCTE 154-4 2008, MPEG Management Information Base SCTE-HMS-MPEG-MIB mpegOutputTSPatInsertRate";
                }
                leaf pmt-insert-rate {
                    type uint8 {
                        range "0..32";
                    }
                    units "tables per second";
                    default 10;
                    description "This attribute represents the PMT table interval expressed in tables/second.";
                    reference "ANSI SCTE 154-4 2008, MPEG Management Information Base SCTE-HMS-MPEG-MIB mpegOutputTSPatInsertRate";
                }
                container yang-ext {
                    ccap:extensionPoint; //different pyang flags impact use of this hint
                    description "node for vendor YANG extensions";
                }
            }
            list video-input-ts {
                key input-ts-index;
                description
                    "The VideoInputTs object configures a given MPEG-2 Transport stream that may be unicast or multicast.";

                leaf input-ts-index {
                    type uint32;
                    description
                      "This is the index for an instance of the video-input-ts list";
                }
                leaf input-ts-name {
                    type string;
                    default " ";
                    description "This attribute configures a name for the input TS. ";
                }
                leaf input-ts-decryption-enabled {
                    type boolean;
                    default false;
                    description
                      "This attribute configures whether this input stream is encrypted for transport across the WAN. This WAN encryption is intended to be removed at the CCAP and not related to any CA encryption that may be configured for the output stream. A value of true means that the CCAP needs to decrypt this input stream as applicable. A value of false means that the CCAP does not need to decrypt this input stream.";
                }
                choice input-ts {
                	mandatory true;
                	case unicast-video-input-ts {
	                        choice unicast-destination {
	                            mandatory true;
	                            case address {
	                                leaf unicast-ts-destination-ip-address {
	                                    type inet:ip-address;
	                                    mandatory true;
	                                    description "This attribute corresponds to the IP destination address of the UDP IP flow of the input TS.";
	                                }
	                            }
	                            case interface {
	                                leaf unicast-ts-interface-name{
	                                    type string;
	                                    mandatory true;
	                                    description "Local IP interface; must be a configured ip-interface name. This association provides a static mapping of an input transport stream to an IP interface";
	                                }
	                            }
	                        }
                            leaf unicast-ts-destination-udp-port {
                                type inet:port-number;
                                mandatory true;
                                description "This attribute corresponds to the UDP destination port of the UDP IP flow of the input TS.";
                            }
                            container yang-ext1 {
                                ccap:extensionPoint; //different pyang flags impact use of this hint
                                description "node for vendor YANG extensions";
                            }
                        }
                	case multicast-video-input-ts {
                            list multicast-ts {
                                key "multicast-ts-source-ip-address multicast-ts-destination-ip-address";
                                min-elements 1;
                                max-elements 2;
                                description "This object specifies the multicast flows of an input transport stream. Having two MulticastTsVideoInput objects for one InputTs occurs when input TS redundancy is configured (Hot-Hot sparing). If two MulticastTsVideoInput objects have the same Priority, this implies HOT-HOT redundancy. Which stream is actually forwarded is vendor-specific.";
                                leaf multicast-ts-source-ip-address {
                                    type inet:ip-address;
                                    mandatory true;
                                    description "This attribute corresponds to the Source Specific Multicast IP Address of the UDP IP flow.";
                                }
                                leaf multicast-ts-destination-ip-address {
                                    type inet:ip-address;
                                    mandatory true;
                                    description "This attribute corresponds to the group address of a SSM (Source Specific Multicast) origination input TS.";
                                }
                                leaf multicast-ts-destination-udp-port {
                                    type inet:port-number;
                                    default 0;
                                    description "This attribute corresponds to the UDP destination port of the UDP IP flow of the input TS.";
                                }
                                leaf multicast-ts-priority {
                                    type int8;
                                    mandatory true;
                                    description "This attribute is a number that identifies the preference order of this transport stream; higher number indicates a higher priority. It is used to order the multicast transport stream for the purpose of redundancy in the case of multiple multicast video sources. If two entries have the same 'Priority', it implies Hot-Hot redundancy.";
                                }
                                leaf multicast-ts-interface-name{
                                    type string;
                                    description "Local IP interface; must be a configured ip-interface name. This association provides a static mapping of an input transport stream to an IP interface";
                                }
                                container yang-ext {
                                    ccap:extensionPoint; //different pyang flags impact use of this hint
                                    description "node for vendor YANG extensions";
                                }
                            }
                            container yang-ext2 {
                                ccap:extensionPoint; //different pyang flags impact use of this hint
                                description "node for vendor YANG extensions";
                            }
                    }
                    case yang-choice-ext {
                        ccap:extensionPoint; //different pyang flags impact use of this hint
                        description "node for vendor YANG extensions";
                    }
                }
                container yang-ext {
                    ccap:extensionPoint; //different pyang flags impact use of this hint
                    description "node for vendor YANG extensions";
                }
            }
            list static-udp-map {
                key udp-map-index;
                min-elements 0;
                description "This object represents the UDP port ranges used for static video sessions.";
                uses udp-map;
                leaf static-video-output-ts {
                    mandatory true;
                    type leafref {
                        path "/ccap/video/video-output-ts/output-ts-index";
                    }
                    description "Reference to video-output-ts index.";
                }
                container yang-ext {
                    ccap:extensionPoint; //different pyang flags impact use of this hint
                    description "node for vendor YANG extensions";
                }
            }
            list reserved-udp-map {
                key udp-map-index;
                min-elements 0;
                description "This object represents reserved ports to be used for non-video applications.";
                uses udp-map;
                container yang-ext {
                    ccap:extensionPoint; //different pyang flags impact use of this hint
                    description "node for vendor YANG extensions";
                }
            }
            list reserved-pid-range {
                key reserved-pid-range-index;
                min-elements 0;
                description "This object represents reserved PID range to not be used on ERM assignments.";
                leaf reserved-pid-range-index {
                    type uint32;
                    mandatory true;
                    description "This key represents the unique identifier of an instance in this object.";
                }
                leaf starting-pid {
                    type uint32;
                    default 0;
                    description "This attribute represents the PID range starts for other applications reserved PIDs.";
                }
                leaf count {
                    type uint32;
                    default 0;
                    description "This attribute represents the number of reserved PIDs starting from 'StartingPid' attribute value.";
                }
                leaf description {
                    type string;
                    default "";
                    description "This attribute represents the description associated with a PID range configured instance.";
                }
                container yang-ext {
                    ccap:extensionPoint; //different pyang flags impact use of this hint
                    description "node for vendor YANG extensions";
                }
            }
            list input-registration {
                key input-registration-name;
                min-elements 0;
                description "This object represents the configuration of Edge ERRP parameters.";
                leaf input-registration-name {
                    type string;
                    mandatory true;
                    description "This key represents the Input interface name. This name corresponds to the [RFC 4133], ENTITY-MIB entPhysicalName.";
                    reference "RFC 4133 ENTITY-MIB entPhysicalName";
                }
                leaf group-name {
                    type string;
                    description "This attribute represents the name of the Edge Input Group associated with this input. This parameter is used in the ERRP Edge Input attribute.";
                }
                leaf erm-name {
                    type string;
                    description "This attribute represents the ERM where the QAM channel is advertised. If empty, the QAM channel is not advertised.";
                }
                leaf bandwidth {
                    type uint32;
                    default 0;
                    description "This attribute represents the bandwidth of the edge input to be advertised. If zero or not present, the CCAP advertises the full bandwidth of the edge input. If the attribute erm-managed-input is set to false, operators should set the bandwidth attribute to a value that greatly exceeds the speed of the input interface; this will cause the ERM to not actively manage the input bandwidth.";
                }
                leaf erm-managed-input {
                    type boolean;
                    mandatory true;
                    description "This attribute allows the Operator to configure whether or not the ERM should manage the input bandwidth on this EdgeInput Interface. A value of true indicates that the ERM will manage the input bandwidth; a value of false indicates that the CCAP will manage the input bandwidth. If set to false, operators should set the bandwidth attribute to a value that greatly exceeds the speed of the input interface so that the ERM will not actively manage the input bandwidth.";
                }
                container yang-ext {
                    ccap:extensionPoint; //different pyang flags impact use of this hint
                    description "node for vendor YANG extensions";
                }
            }
            list pid-session {
                key session-index;
                min-elements 0;
                description "The PidSession object allows the identification, processing and insertion of a single PID stream into exactly one OutputTs. Each PidSession object must have one InputTs object associated with it.";
                uses video-session-group;
                leaf input-pid {
                    type uint16 {
                        range "0..8191 | 65535";
                    }
                    mandatory true;
                    description "This attribute identifies a specific PID stream in the input transport stream.";
                    reference "ANSI SCTE 154-5 2008, SCTE-HMS-HEADENDIDENT TEXTUAL CONVENTIONS MIB HePidValue.";
                }
                leaf pid-remap-enable {
                    type boolean;
                    default false;
                    description "This object configures whether or not the identified PID stream can be remapped when inserted in the OutputTs.";
                }
                leaf pid-type {
                    type video-pid-usage-type;
                    mandatory true;
                    description "This enumeration defines the type of the identified PID stream. This value is used to understand what anchor table (i.e., PAT, CAT) would need to be updated, in case PidRemapEnable is set to True and a remap is required.";
                }
                leaf cas-id {
                    type ccap-octet-data-type {
                       length "8";
                    }
                    default 00000000;
                    description "This attribute allows a proper identification of the CAT table parameter(s) that need(s) to be updated when the PidType is set to 'EMM', PidRemapEnable is set to True and a remap is required. This parameter is required in Simulcrypt operation, when the CAT advertises more than one EMM PID streams. Zero means no CAS is associated with this PID session.";
                }
                leaf output-pid {
                    type uint16 {
                        range "0..8191 | 65535";
                    }
                    description "This attribute defines the expected PID value of the identified PID stream when inserted in the OutputTS. However, the OutputPid value cannot be guaranteed if the pid-remap-enable flag is set to True.";
                    reference "ANSI SCTE 154-5 2008, SCTE-HMS-HEADENDIDENT TEXTUAL CONVENTIONS MIB HePidValue.";
                }
                leaf output-program-number {
                	type uint16;
                	description "This attribute identifies the output program number for this PID Session.";
                }
                container yang-ext {
                    ccap:extensionPoint; //different pyang flags impact use of this hint
                    description "node for vendor YANG extensions";
                }
            }
            list program-session {
                key session-index;
                min-elements 0;
                description "The ProgramSession object allows the identification, encryption, processing and insertion a single program stream into exactly one OutputTs. Each ProgramSession object must have one or two InputTs objects associated with it. Having two InputTs objects associated with it occurs when input TS redundancy is configured (Hot-Hot sparing).";
                uses video-session-group;
                leaf input-mpeg-program-number {
                    type uint16;
                    mandatory true;
                    description "This attribute selects a specific program from the transport stream of the incoming video stream. This program number should be part of the incoming PAT. A value of 0 (zero) means that any incoming program number can be accepted.";
                }
                leaf output-mpeg-program-number {
                    type uint16;
                    mandatory true;
                    description "This attribute specifies the program number to be present in the transport stream of the outgoing video stream. This program number will be part of the outgoing PAT.";
                }
                leaf pat-pid-remap {
                    type boolean;
                    default true;
                    description "A value true indicates that the elementary stream PID of this input program can be remapped to the output TS, as long as the PAT and PMT are updated. A value false indicates that the same input elementary stream PID has to be used on the output TS.";
                }
                leaf requested-bandwidth {
                    type uint32;
                    units bps;
                    mandatory true;
                    description "This attribute configures the expected bandwidth parameters for a static input video session described by this object. This parameter is used for encryption and video down channel output resources. A value of 0 (zero) means that no bandwidth validation is required.";
                }
                leaf cas-info {
                    type leafref {
                        path "/ccap/video/cas-info/cas-info-index";
                    }
                    description "Reference to a cas-info index.";
                }
                leaf encryption-data {
                    type leafref {
                        path "/ccap/video/encryption-data/encryption-data-index";
                    }
                    description "A reference to encryption-data index.";
                }
                leaf encrypt-control {
                    type leafref {
                        path "/ccap/video/encrypt-control/encrypt-control-index";
                    }
                    description "A reference to encrypt-control index.";
                }
                container yang-ext {
                    ccap:extensionPoint; //different pyang flags impact use of this hint
                    description "node for vendor YANG extensions";
                }
            }
            list cas-info {
                key cas-info-index;
                min-elements 0;
                description 
                    "The cas-info object serves two purposes: 
                     1. It identifies the ECMG(s) that need(s) to be involved in the encryption of the program session. In the case of a Simulcrypt operation, more than one CasInfo object can be attached to the same ProgramSession.
                     2. It defines a CA-specific opaque object that needs to be forwarded to the appropriate ECMG when the session is initialized. ";
                leaf cas-info-index {
                    type uint32;
                    mandatory true;
                    description "This attribute configures the index for an instance of CasInfo for a given ProgramSession.";
                }
                leaf cas-id {
                    type ccap-octet-data-type {
                       length "8";
                    }
                    mandatory true;
                    description "CasId is the 32 bit hexadecimal representation of the CAS system identifier.";
                }
                leaf ca-blob {
                    type string;
                    mandatory true;
                    description "CaBlob is opaque data that the Encryptor is required to forward to the ECMG associated with the specified CasId.";
                }
                container yang-ext {
                    ccap:extensionPoint; //different pyang flags impact use of this hint
                    description "node for vendor YANG extensions";
                }
            }
            list mpts-passthrough-session {
                key session-index;
                min-elements 0;
                description "The mpts-passthrough-session object allows the identification and insertion of an unmodified MPTS into exactly one OutputTs. Each MptsPassThruSession object must have one or two InputTs objects associated with it. Having two InputTs objects associated with it occurs when input TS redundancy is configured (Hot-Hot sparing).";
                uses video-session-group;
                container yang-ext {
                    ccap:extensionPoint; //different pyang flags impact use of this hint
                    description "node for vendor YANG extensions";
                }
            }
            list encryption-data {
                key encryption-data-index;
                min-elements 0;
                description "The EncryptionData object allows a per video session encryption configuration.";
                leaf encryption-data-index {
                    type uint32;
                    mandatory true;
                    description "The index is the key for the EncryptionData object.";
                }
                leaf cci-level {
                    type cci-level-type;
                    mandatory true;
                    description "This attribute represents the Copy Control Indicator/Digital Rights protection applicable to the program. It is forwarded to all active ECMGs to be encapsulated into ECMs.";
                }
                leaf cit {
                    type cit-type;
                    mandatory true;
                    description "This attribute represents the Constrained Image Trigger flag applicable to the program. It is forwarded to all active ECMGs to be encapsulated into ECMs.";
                }
                leaf rct {
                    type rct-type;
                    mandatory true;
                    description "This attribute represents the Redistribution Control Trigger flag applicable to the program. It is forwarded to all active ECMGs to be encapsulated into ECMs.";
                }
                leaf cci-reserved {
                    type cci-reserved-type;
                    mandatory true;
                    description "This attribute reserves 2 bits of copy control information (CCI) for future use. It is forwarded to all active ECMGs to be encapsulated into ECMs.";
                }
                leaf provider-asset-id {
                    type string {
                        length "1..255";
                    }
                    mandatory true;
                    description "This attribute configures the Provide Asset Id parameter that is passed in the initial RTSP session SETUP (e.g., for VOD) to the Encryptor and enables the Encryptor to uniquely identify/reference the VOD asset or broadcast channel. ";
                }
                container yang-ext {
                    ccap:extensionPoint; //different pyang flags impact use of this hint
                    description "node for vendor YANG extensions";
                }
            }
            list encrypt-control {
                key encrypt-control-index;
                min-elements 0;
                description "This configuration object selects the encryption option of a static encryption session. The CaEncryptionMode is not defined as only one mode and is supported per Encryptor.";
                leaf encrypt-control-index {
                    type uint32;
                    mandatory true;
                    description "This attribute configures the index for an instance of EncryptControl for a given ProgramSession.";
                }
                leaf encryption-scheme {
                    type encryption-scheme-type;
                    mandatory true;
                    description "This attribute defines the encryption algorithm to be used for a given video session. The value of other(1) is used when a vendor-extension has been implemented for this attribute.";
                }
                leaf block-stream-until-encrypted {
                    type boolean;
                    default true;
                    description "BlockStreamUntilEncrypted indicates if the encryption engine should block the program until it can encrypt it (i.e., it has received a first Encryption Control Message (ECM) and Control Word (CW) from the ECMG) or release it in the clear to the destination or output. Values are 0 meaning false or 1 meaning true. Note that this parameter can be used to enforce synchronous behavior, wherein the RTSP server (i.e., Encryption Engine) will not acknowledge the session request back to the ERM until it has actually started to encrypt the stream. Obviously, this assurance comes at the expense of setup latency.";
                }
                leaf key-length {
                    type key-length-type;
                    mandatory true;
                    description "This attribute configures the number of bits in the encryption keys used by encryption algorithm defined by the EncryptionScheme attribute.";
                }
                leaf encryptor-opaque {
                    type string;
                    mandatory true;
                    description "EncryptorOpaque holds private data used by the Encryptor that may be under CA license from the CA vendor.";
                }
                container yang-ext {
                    ccap:extensionPoint; //different pyang flags impact use of this hint
                    description "node for vendor YANG extensions";
                }
            }
            list ecmd {
                key ecm-index;
                min-elements 0;
                description "This object allows for the configuration of the interface to an Entitlement Control Message Decoder (ECMD). ";
                uses ecm-group;
                leaf number-decrypted-streams {
                    type uint32;
                    mandatory true;
                    description "The maximum number of decrypted streams the ECMD should handle.";
                }
                container yang-ext {
                    ccap:extensionPoint; //different pyang flags impact use of this hint
                    description "node for vendor YANG extensions";
                }
            }
            list ecmg {
                key ecm-index;
                min-elements 0;
                description "This object allows for the configuration of the interface to an Entitlement Control Message Generator (ECMG).  Redundant ECMGs for the same CAS may exist, each with the same CA_System_ID, with the priority determining which is currently in use by an Encryptor for a particular CAS. ";
                uses ecm-group;
                leaf recommended-cp-duration {
                    type uint32 {
                        range "1..4294967295";
                    }
                    units seconds;
                    mandatory true;
                    description "The recommended cryptoperiod, in seconds, the ECMG should expect.";
                }
                leaf number-encrypted-streams {
                    type uint32;
                    units streams;
                    mandatory true;
                    description "The maximum number of encrypted streams the ECMG should handle.";
                }
                container yang-ext {
                    ccap:extensionPoint; //different pyang flags impact use of this hint
                    description "node for vendor YANG extensions";
                }
            }
            list erm-registration {
                key erm-name;
                min-elements 0;
                description "This object allows for the configuration of the interface to an Edge Resource Manager. Only one configured ERM interface exists for the entire CCAP. An ErmRegistration object contains the attributes in the following table. The CCAP MAY support only one instance of the ErmRegistration object. Configuring more than one ERM is generally used for scaling purposes, with each individual ERM being focused on specific, unique service groups. More than one ERM cannot be practically used to support the same service group, and there could be conflicts between the control messages of the independent ERMs.";
                leaf erm-name {
                    type string;
                    mandatory true;
                    description "This key represents the name of the ERM related to this registration instance. This is an internal reference for associating, e.g., QAM channels and input interfaces to an ERM.";
                }
                container erm-address {
                    uses host;
                    description "This attribute represents the IP address/hostname of the ERM. ";
                }
                leaf erm-port {
                    type inet:port-number;
                    default 0;
                    description "This attribute represents the TCP port number used to reach the ERM.";
                }
                leaf erm-connection-mode {
                    type erm-connection-mode-type;
                    default client;
                    description "This attribute represents the type of TCP connection that is established by the CCAP.";
                }
                leaf hold-timer {
                    type uint16 {
                        range "0 | 3..3600";
                    }
                    units seconds;
                    default 240;
                    description 
                        "This attribute represents the number of seconds that the sender proposes for the value of the hold timer. Upon receipt of an OPEN message, the CCAP MUST calculate the value of the Hold Timer by using the smaller of its configured Hold Time and the Hold Time received in the OPEN message.
                         The Hold Time has to be either zero or at least three seconds. 
                         An implementation MAY reject connections on the basis of the Hold Time. The calculated value indicates the maximum number of seconds that may elapse between the receipt of successive KEEPALIVE and/or UPDATE messages by the sender..";
                }
                leaf connection-retry-timer {
                    type uint32;
                    units seconds;
                    default 20;
                    description "This attribute represents the time in seconds for the connect retry timer. The exact value of the connect retry timer is a local matter, but should be sufficiently large to allow TCP initialization.";
                }
                leaf next-hop-address-domain {
                    type uint32;
                    mandatory true;
                    description "This attribute represents the address domain number of the next-hop server. The NextHopServer specifies the address to which a manager should use to connect to the component in order to control the resource specified in the reachable route. This parameter is used in the ERRP NextHopServer attribute.";
                }
                container comp-address {
                    uses host;
                    description "This attribute is the IP address/hostname of the ERRP NextHopServer.";
                }
                leaf comp-port {
                	type inet:port-number;
                	default 6069;
                	description "This attribute represents the ERRP NextHopServer attribute port number. Only used if comp-address is configured.";
                }
                leaf streaming-zone {
                    type string {
                        length "1..255";
                    }
                    mandatory true;
                    description 
                        "This attribute represents the Streaming Zone within which the component operates. This parameter is used in the ERRP OPEN message. StreamingZone Name is a mandatory parameter when supporting video applications. The capability is optional when signaling DOCSIS only resources. Since the target for ERM configuration is video, this element is mandatory.
                         The value is to be set to the string that represents the StreamingZone Name, i.e., <region>. The characters comprising the string are in the set within TEXT defined in section 15.1 of [RFC 2326]. The CCAP MUST support minimum string lengths of 64; however, the composition of the string used is defined by implementation agreements specified by the service provider.
                         A CCAP will exist in a single streaming zone.";
                    reference "RFC 2326 Section 15.1";
                }
                leaf id {
                    type uint32;
                    default 0;
                    description "This attribute represents the unique identifier for the CCAP device within its Streaming Zone. This value can be set to the 4-octet value of an IPv4 address assigned to that device. This ID value is determined on startup and is the same for all peer connections. This parameter is used in the ERRP OPEN message header.";
                }
                leaf cost {
                    type uint32;
                    default 0;
                    description "This attribute represents the static cost for use of this resource.";
                }
                leaf comp-name {
 			        type string {
			            length "1..255";
			        }
                    mandatory true;
                    description 
                        "The name of the component for which the data in the update message applies. This parameter is used in the ERRP OPEN message. Component Name is a mandatory parameter when supporting video applications. The capability is optional when signaling DOCSIS only resources. Since the target for ERM configuration is video, this element is mandatory.
                         The value is to be set to the string that represents the Component Name, i.e., <region>.<localname>. The characters comprising the string are in the set within TEXT defined in section 15.1 of [RFC 2326]. The CCAP MUST support minimum string lengths of 64; however, the composition of the string used is defined by implementation agreements specified by the service provider.";
                    reference "RFC 2326 Section 15.1";
                }
                container yang-ext {
                    ccap:extensionPoint; //different pyang flags impact use of this hint
                    description "node for vendor YANG extensions";
                }
            }
            list video-output-ts {
                key output-ts-index;
                min-elements 0;
                description "The video-output-ts element is an intermediate object that represents a configuration multiplex of one or more ProgramSession instances.";
                leaf output-ts-index {
                    type uint32;
                    mandatory true;
                    description "This is not a tsid. It uniquely identifies a CCAP-generated MPTS composed of one or more program streams, PID streams and/or pass thru MPTS.";
                }
                leaf output-ts-name {
                    type string;
                    default "";
                    description "This attribute configures the name of this instance of video-output-ts.";
                }
                list video-down-channel-ref {
                    key "slot ds-rf-port down-channel";
                    min-elements 1;
                    description "Reference to a list of video down channels, all of which will transmit this MPTS.";
                    uses video-down-channel-reference;
                    container yang-ext {
                        ccap:extensionPoint; //different pyang flags impact use of this hint
                        description "node for vendor YANG extensions";
                    }
                }
                container yang-ext {
                    ccap:extensionPoint; //different pyang flags impact use of this hint
                    description "node for vendor YANG extensions";
                }
            }
            list static-udp-map-encryption {
                key udp-map-encryption-index;
                leaf udp-map-encryption-index {
                    type uint8;
                }
                leaf cas-info {
                    mandatory true;
                    type leafref {
                        path "/ccap/video/cas-info/cas-info-index";
                    }
                    description "Reference to a cas-info index.";
                }
                leaf encryption-data {
                    type leafref {
                        path "/ccap/video/encryption-data/encryption-data-index";
                    }
                    description "A reference to encryption-data index.";
                }
                leaf encrypt-control {
                    mandatory true;
                    type leafref {
                        path "/ccap/video/encrypt-control/encrypt-control-index";
                    }
                    description "A reference to encrypt-control index.";
                }
                container yang-ext {
                    ccap:extensionPoint; //different pyang flags impact use of this hint
                    description "node for vendor YANG extensions";
                }
            }
            container yang-ext {
                ccap:extensionPoint; //different pyang flags impact use of this hint
                description "node for vendor YANG extensions";
            }
        }
        container epon {
            description "The epon object is the primary container of EPON configuration objects.";
            container oam-config {
                description "This object controls the rate at which OAM messages are sent on the EPON interface.";
                reference 
                    "DOCSIS Provisioning of EPON OSSI Specification DPOE-SP-OSSIv1.0-I01-110225
                     EPON OAM Configuration section.";
                leaf min-oam-rate {
                    type uint8;
                    units "PDUs per second";
                    default 1;
                    description "The minimum number of OAM PDUs per second that will be generated by the OLT. If no other OAM PDU is generated at the minimum rate, the OLT will generate an OAM Information request as a 'heartbeat' message. A value of zero indicates that no heartbeat request will be generated.";
                    reference 
                        "DOCSIS Provisioning of EPON OSSI Specification DPOE-SP-OSSIv1.0-I01-110225
                         EPON OAM Configuration section.";
                }
                leaf max-oam-rate {
                    type uint8;
                    units "PDUs per second";
                    default 30;
                    description "The maximum number of OAM PDUs per second that can be exchanged between the OLT and the ONU on a particular EPON link.";
                    reference 
                        "DOCSIS Provisioning of EPON OSSI Specification DPOE-SP-OSSIv1.0-I01-110225
                         EPON OAM Configuration section.";
                }
                leaf oam-response-timeout {
                    type uint8;
                    units seconds;
                    default 1;
                    description "The maximum time (in seconds) that the OLT will wait for a response from the ONU for a given OAM PDU request.";
                    reference 
                        "DOCSIS Provisioning of EPON OSSI Specification DPOE-SP-OSSIv1.0-I01-110225
                         EPON OAM Configuration section.";
                }
                container yang-ext {
                    ccap:extensionPoint; //different pyang flags impact use of this hint
                    description "node for vendor YANG extensions";
                }
            }
            container loop-timing-config {
                description "This object configures the loop timing for EPON interfaces.";
                reference "DOCSIS Provisioning of EPON OSSI Specification DPOE-SP-OSSIv1.0-I01-110225 Loop Timing section.";
                leaf min-propagation-delay {
                    type uint16;
                    units "16 ns TQ";
                    default 0;
                    description "The one way propagation delay (in 16ns units) on the fiber to the closest ONU.";
                    reference "DOCSIS Provisioning of EPON OSSI Specification DPOE-SP-OSSIv1.0-I01-110225 LoopTiming section.";
                }
                leaf max-propagation-delay {
                    type uint16;
                    units "16 ns TQ";
                    default 6250;
                    description "The one way propagation delay (in 16ns units) on the fiber to the farthest ONU.";
                    reference "DOCSIS Provisioning of EPON OSSI Specification DPOE-SP-OSSIv1.0-I01-110225 LoopTiming section.";
                }
                leaf onu-delay {
                    type uint16 {
                        range "3125..65535";
                    }
                    units "16 ns TQ";
                    default 3125;
                    description "The processing time (in 16ns units) required by an ONU.";
                    reference "DOCSIS Provisioning of EPON OSSI Specification DPOE-SP-OSSIv1.0-I01-110225 LoopTiming section.";
                }
                container yang-ext {
                    ccap:extensionPoint; //different pyang flags impact use of this hint
                    description "node for vendor YANG extensions";
                }
            }
            container mpcp-config {
                description "This object configures the Multi-Point Control Protocol for EPON interfaces.";
                reference "[DPoE OSSI], MPCP Configuration section";
                leaf discovery-period {
                    type uint16 {
                        range "10..65530";
                    }
                    units msec;
                    default 1000;
                    description "The period (in msecs) used by the OLT to generate discovery gates.";
                    reference "DOCSIS Provisioning of EPON OSSI Specification DPOE-SP-OSSIv1.0-I01-110225 MPCP Configuration section.";
                }
                leaf grant-size-in-discovery-gate {
                    type uint32 {
                        range "84..131070";
                    }
                    units Bytes;
                    default 16319;
                    description "The OLT's announced discovery grant length (in bytes).";
                    reference "DOCSIS Provisioning of EPON OSSI Specification DPOE-SP-OSSIv1.0-I01-110225 MPCP Configuration section.";
                }
                leaf deregistration-timeout {
                    type uint32 {
                        range "0..4294967295";
                    }
                    units msec;
                    default 0;
                    description "The amount of time (in msecs) the OLT will wait for successive ONU MPCP Report PDUs before deregistering the ONU.";
                    reference "DOCSIS Provisioning of EPON OSSI Specification DPOE-SP-OSSIv1.0-I01-110225 MPCP Configuration section.";
                }
                container yang-ext {
                    ccap:extensionPoint; //different pyang flags impact use of this hint
                    description "node for vendor YANG extensions";
                }
            }
            list deny-onu {
                key onu-mac-address;
                leaf onu-mac-address {
                    type yang:mac-address;
                    description "The MAC address of the ONU that will be added to the deny list.";
                }
                container yang-ext {
                    ccap:extensionPoint; //different pyang flags impact use of this hint
                    description "node for vendor YANG extensions";
                }
            }
            list epon-mac-domain-config {
                key mac-domain-name;
                min-elements 0;
                description "This object defines a specialization of the MacDomain object for EPON interfaces.";
                uses mac-domain-configuration-group;
                list one-gb-epon-interface {
                    key "epon-slot epon-port-number";
                    min-elements 0;
                    description "This configuration object allows for a one Gigabit EPON port to be assigned to this epon-mac-domain. ";
                    uses epon-one-gb-port-reference;
                    container yang-ext {
                        ccap:extensionPoint; //different pyang flags impact use of this hint
                        description "node for vendor YANG extensions";
                    }
                }
                list ten-gb-epon-interface {
                    key "epon-slot epon-port-number";
                    min-elements 0;
                    description "This configuration object allows for a symmetric or asymmetric ten Gigabit EPON port to be assigned to this epon-mac-domain.";
                    uses epon-ten-gb-port-reference;
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
        container network {
            description "Network is the primary container of network configuration objects.";
            list dns-resolver {
                key domain-suffix;
                min-elements 0;
                max-elements 1;
                description "This object allows the configuration of DNS servers and the configuration of default domain suffix information.  The objects in this configuration object are scalars.";
                leaf domain-suffix {
                    type string;
                    description "The attribute DomainSuffix configures a Domain Suffix that should be post-pended to any hostname lookup that does not consist of a Fully Qualified Domain Name (FQDN).";
                }
                leaf enabled {
                    type boolean;
                    default true;
                    description "This attribute configures if the associated domain suffix should be applied to hostnames that do not include a Fully Qualified Domain Name (FQDN).";
                }
                container yang-ext {
                    ccap:extensionPoint; //different pyang flags impact use of this hint
                    description "node for vendor YANG extensions";
                }
            }
            list dns-server {
                key dns-server-index;
                min-elements 0;
                description "This object allows the configuration of the different DSN Servers that the CCAP can use to get Domain Name Resolution.";
                leaf dns-server-index {
                    type uint32;
                    description "This attribute configures the index for this instance of DnsServer.";
                }
                leaf server-ip {
                    type inet:ip-address;
                    mandatory true;
                    description "This attribute configures the IP address of the DNS server used by the CCAP for DNS resolution. No distinction is made for IPv6 or IPv4 addresses here.";
                }
                container yang-ext {
                    ccap:extensionPoint; //different pyang flags impact use of this hint
                    description "node for vendor YANG extensions";
                }
            }
            list integrated-servers {
                key "server-type local-listener-port";
                min-elements 0;
                description "This configuration object defines the types of servers integrated into the CCAP and their respective administrative states.";
                leaf server-type {
                    type integrated-server-type;
                    mandatory true;
                    description "The type of server being configured on the CCAP.";
                }
                leaf local-listener-port {
                    type inet:port-number;
                    mandatory true;
                    description "The second part of the key for this object configures the TCP or UDP port number on which the server listens. The CCAP MUST assign the default value as the IANA-assigned port number associated with the ServerType selected, as defined by IANA.";
                    reference "Port Numbers, IANA, http://www.iana.org/assignments/port-numbers";
                }
                leaf enabled {
                    type boolean;
                    default false;
                    description "This attribute configures the running state of the server.  True means that the server will actively listen on the specified port.  False means that the specific server is disabled.";
                }
                leaf listener-ip-interface-name {
                    type string;
                    description "Local IP interface; must be a configured ip-interface name. This specifies the IP interface on which the server listens. If an IP interface is not specified, the behavior of the CCAP is vendor specific.";
                }
                container yang-ext {
                    ccap:extensionPoint; //different pyang flags impact use of this hint
                    description "node for vendor YANG extensions";
                }
            }
            container ssh-server {
                description "This configuration object defines the types of servers integrated into the CCAP and their respective administrative states.";
                leaf ssh-local-listener-port {
                    type inet:port-number;
                    default 22;
                    description "The second part of the key for this object configures the TCP or UDP port number on which the server listens. The CCAP MUST assign the default value as the IANA-assigned port number associated with the ServerType selected, as defined by IANA.";
                    reference "Port Numbers, IANA, http://www.iana.org/assignments/port-numbers";
                }
                leaf enabled {
                    type boolean;
                    default false;
                    description "This attribute configures the running state of the server.  True means that the server will actively listen on the specified port.  False means that the specific server is disabled.";
                }
                leaf cipher {
                    type cipher-type;
                    default des3;
                    description "This attribute configures the set of encryption algorithms that
                                 are allowed on the SSH interface. SSH will use the enabled set
                                 of algorithms to negotiate the algorithm to use with the connecting
                                 client. The CCAP system MUST log an error if the configuration
                                 file enables a cipher algorithm that is not supported. The bit
                                 setting of 'other' may be used to enable an algorithm supported
                                 by the CCAP that is not in the defined list.";
                }
                leaf message-auth-code {
                    type auth-code-type;
                    description "This attribute configures the set of encryption algorithms that
                                 are allowed on the SSH interface. SSH will use the enabled set of
                                 algorithms to negotiate the algorithm to use with the connecting
                                 client. The CCAP system MUST log an error if the configuration
                                 file enables a cipher algorithm that is not supported. The bit
                                 setting of 'other' may be used to enable an algorithm supported
                                 by the CCAP that is not in the defined list.";
                }
                leaf host-authentication {
                    type host-auth-type;
                    default none;
                    description "This attribute enables SSH host authentication using public keys
                                 in a specified format. It is assumed that user authentication
                                 will be configured in the same way as other CCAP interfaces. The
                                 file format for key storage is outside the scope of this specification.";
                }
                leaf listener-ip-interface-name {
                    type string;
                    description "Local IP interface; must be a configured ip-interface name. This specifies the IP interface on which the server listens. If an IP interface is not specified, the behavior of the CCAP is vendor specific.";
                }
                container yang-ext {
                    ccap:extensionPoint; //different pyang flags impact use of this hint
                    description "node for vendor YANG extensions";
                }
            }
            container telnet-server {
                description "This configuration object defines an integrated Telnet server in the CCAP.";
                leaf telnet-local-listener-port {
                    type inet:port-number;
                    default 23;
                    description "The second part of the key for this object configures the TCP or UDP port number on which the server listens. The CCAP MUST assign the default value as the IANA-assigned port number associated with the ServerType selected, as defined by IANA.";
                    reference "Port Numbers, IANA, http://www.iana.org/assignments/port-numbers";
                }
                leaf enabled {
                    type boolean;
                    default false;
                    description "This attribute configures the running state of the server.  True means that the server will actively listen on the specified port.  False means that the specific server is disabled.";
                }
                leaf listener-ip-interface-name {
                    type string;
                    description "Local IP interface; must be a configured ip-interface name. This specifies the IP interface on which the server listens. If an IP interface is not specified, the behavior of the CCAP is vendor specific.";
                }
                container yang-ext {
                    ccap:extensionPoint; //different pyang flags impact use of this hint
                    description "node for vendor YANG extensions";
                }
            }
            list authentication-policy {
                key "protocol policy";
                min-elements 0;
                description "This configuration object allows the configuration of authentication and accounting services. The Priority attribute controls which service is used first for authenticating users.";
                leaf policy {
                    type policy-type;
                    description "This attribute is the first part of the key and configures the policy type for the specified protocol.";
                }
                leaf protocol {
                    type protocol-type;
                    description "This attribute is the second part of the key and represents the protocol used by the AAA server.";
                }
                leaf priority {
                    type uint32;
                    mandatory true;
                    description "This attribute sets a priority for the protocol selected. Higher numbers are higher priority.";
                }
                container yang-ext {
                    ccap:extensionPoint; //different pyang flags impact use of this hint
                    description "node for vendor YANG extensions";
                }
            }
            list local-authorization {
                key username;
                min-elements 0;
                description "Local-authorization configures the local user accounts and privilege levels.";
                leaf username {
                    type string;
                    description "This attribute configures the login name to be used.";
                }
                leaf privilege-level {
                    type uint16 {
                        range "0..15";
                    }
                    mandatory true;
                    description "This attribute correspond to the user's privilege level. The highest number provides the most user privileges.";
                }
                leaf password {
                    type string;
                    mandatory true;
                    description "This attribute correspond to the user's password. Upon export, the CCAP MUST export the Password attribute of the LocalAuth object encrypted with a vendor-specific algorithm.";
                }
                leaf clear-key {
                    type boolean;
                    mandatory true;
                    description "This attribute indicates whether the Key/Password attribute is in the clear (true) or encrypted (false). This attribute defines the status of the key/password (encrypted or decrypted), not whether the device should export the key/password in the clear or encrypted. Regardless of the value of this setting, the key/password will always be exported encrypted. ";
                }
                container yang-ext {
                    ccap:extensionPoint; //different pyang flags impact use of this hint
                    description "node for vendor YANG extensions";
                }
            }
            list radius {
                key auth-server-index;
                min-elements 0;
                description "Radius creates the configuration for Radius servers.";
                uses authorizer-group;
                leaf radius-auth-port {
                    type inet:port-number;
                    default 1812;
                    description "This attribute defines the TCP port on which AAA authentication and authorization are performed.";
                }
                leaf accounting-port {
                    type inet:port-number;
                    default 1813;
                    description "This attribute defines the TCP port on which AAA accounting is performed.";
                }
                container yang-ext {
                    ccap:extensionPoint; //different pyang flags impact use of this hint
                    description "node for vendor YANG extensions";
                }
            }
            list tacacs-plus {
                key auth-server-index;
                min-elements 0;
                description "Tacacs-plus configures TACACS+ services for the CCAP.";
                uses authorizer-group;
                leaf tacacs-plus-auth-port {
                    type inet:port-number;
                    default 49;
                    description "This attribute defines the TCP port used for communicating with the AAA server.";
                }
                container yang-ext {
                    ccap:extensionPoint; //different pyang flags impact use of this hint
                    description "node for vendor YANG extensions";
                }
            }
            list keychain {
                key key-id;
                min-elements 0;
                description "Keychain allows the CCAP to be configured with different Ripv2 key change information.";
                leaf key-id {
                    type uint32 {
                        range "0..2147483647";
                    }
                    description "This attribute configures a KeyId used in RipV2 route updates.";
                }
                leaf key-string {
                    type string {
                        length "1..79";
                    }
                    mandatory true;
                    description "This attribute configures the actual key used for this instance. This value has to be the same on both the sender and receiver of the RIPv2 route.";
                }
                leaf accept-lifetime {
                    type uint32 {
                        range "0..2147483647";
                    }
                    units seconds;
                    mandatory true;
                    description "This attribute configures the accept lifetime value in seconds for the key in this instance.";
                }
                leaf send-lifetime {
                    type uint32 {
                        range "0..2147483647";
                    }
                    units seconds;
                    default 0;
                    description "This attribute configures the send lifetime value in seconds for the key in this instance. A value of 0 (zero) means that there is no lifetime limit.";
                }
                leaf clear-key {
                    type boolean;
                    mandatory true;
                    description "This attribute indicates whether the key-string attribute is included in the XML configuration file in the clear (true) or encrypted (false). This attribute defines the status of the key (encrypted or decrypted), not whether the device should export the key in the clear or encrypted. Regardless of the value of this setting, the key will always be exported as encrypted.";
                }
                container yang-ext {
                    ccap:extensionPoint; //different pyang flags impact use of this hint
                    description "node for vendor YANG extensions";
                }
            }
            container fail-over {
                description "This object configures the automatic fail-over operation of the CCAP.";
                leaf auto-fail-back {
                    type boolean;
                    default true;
                    description "This attribute configures whether or not the CCAP automatically switches back to a line card after a failover event. If true, when the failed card is operational, the CCAP will begin using that card again. If False, the operator will have to perform the failback operation.";
                }
                container yang-ext {
                    ccap:extensionPoint; //different pyang flags impact use of this hint
                    description "node for vendor YANG extensions";
                }
            }
            container local-time {
                description "Time allows the configuration of a Primary and Secondary NTP server, as well as other local time attributes. This object does not fully configure all NTP client parameters. Vendors may provide additional configuration objects to fully configure the NTP and SNTP protocols if desired.";
                container ntp-master {
                    uses host;
                    description "This attribute represents the Master NTP server.";
                }
                container ntp-backup {
                    presence "Configures a backup NTP Server";
                    choice address-or-hostname {
                        case address {
                            leaf address {
                                mandatory true;
                                type inet:ip-address;
                            }
                        }
                        case name {
                            leaf name {
                                mandatory true;
                                type inet:domain-name;
                            }
                        }
                    }
                    description "This attribute represents the backup NTP Server in case the master NTP fails.";
                }
                leaf time-zone {
                    type string;
                    default 00;
                    description 
                        "This attribute represents the offset value to the local time to arrive at UTC Time. The value has the following format: 
                         hh[:mm] - the hour 
                         (0 <= hh <= 24) - required, minutes 
                         (0 <= mm <= 59) -the mm (minutes) is optional. The hour can be preceded by a minus sign (-).";
                }
                leaf daylight-saving-time-shift-dates {
                    type string;
                    default "3.2.0/02:00,11.1.0/02:00,01";
                    description 
                        "This attribute indicates when to change to and from daylight saving (or summer) time.
                         The value has the form: date1/time1,date2/time2,offset. 
                         The first date describes when the change from standard to daylight saving time occurs, and the second date describes when the change back happens.
                         Each time field describes when, in current local time, the change to the other time is made. 
                         The format of date is the following: m.w.d - The dth day (0 <= d <= 6) of week w of month m of the year (1 <= w <= 5, 1 <= m <= 12, where week 5 means 'the last d day in month m', which may occur in the fourth or fifth week). Week 1 is the first week in which the dth day occurs. Day zero is Sunday. 
                         The time format is the following: hh:mm - The offset value is the value you must add to the local time to arrive at UTC Time during the daylight saving time. The offset value has the following format: hh[:mm].
                         The default value is the second Sunday in March (start) and the first Sunday in November (end).

                         Reference: [PMI], Time Object section";
                }
                leaf dst-recurring-change {
                    type boolean;
                    description "This attribute controls whether the CCAP automatically adjusts the time to Daylight Saving Time (DST). If true, the CCAP will adjust the time based on the value of the DaylightSavingTimeCalendar attribute.";
                    default false;
                }
                leaf source-ip-interface-name {
                    type string;
                    description "Local IP interface; must be a configured ip-interface name. If not specified, then the vendor picks the source IP address";
                }
                container yang-ext {
                    ccap:extensionPoint; //different pyang flags impact use of this hint
                    description "node for vendor YANG extensions";
                }
            }
            container user-terminal
            {
                container console-terminal {
                    uses terminal-service-group;
                    container yang-ext {
                        ccap:extensionPoint; //different pyang flags impact use of this hint
                        description "node for vendor YANG extensions";
                    }
                }
                list virtual-terminal {
                    key vty-index;
                    leaf vty-index {
                        type uint8;
                    }
                    uses terminal-service-group;
                    container yang-ext {
                        ccap:extensionPoint; //different pyang flags impact use of this hint
                        description "node for vendor YANG extensions";
                    }
                }
                container yang-ext {
                    ccap:extensionPoint; //different pyang flags impact use of this hint
                    description "node for vendor YANG extensions";
                }
            }
            list acl
            {
                key acl-name;
                leaf acl-name {
                    type string;
                }
                list ip-acl-rule {
                    key acl-rule-index;
                    min-elements 1;
                    leaf acl-rule-index {
                        type uint16;
                    }
                    choice remark-or-action {
                        mandatory true;
                        case is-remark {
                            leaf remark { type string; mandatory true;}
	                        container yang-ext1 {
	                            ccap:extensionPoint; //different pyang flags impact use of this hint
	                            description "node for vendor YANG extensions";
	                        }
                        }
                        case is-rule {
		                    leaf acl-action {
		                        type authorization-action-type;
		                        default deny;
		                    }
		                    choice address-family {
		                        mandatory true;
		                        case ipv4
		                        {
		                            container ipv4-rule {
			                            description "This rule matches all of the defined elements.
			                                         If no filters are defined, it matches all IPv4 packets.";
			                            list dest-ipv4-addr-filter {
			                                max-elements 1;
			                                key dest-addr;
				                            leaf dest-addr {
				                                mandatory true;
				                                type inet:ipv4-address;
				                            }
				                            leaf dest-wildcard-mask {
				                                mandatory true;
				                                type inet:ipv4-address;
                                                                description "The dest-wildcard-mask attribute defines which bits of the packet's 
                                                                             source IP address are matched to the dest-wildcard-mask attribute. The 
                                                                             usage of the IP address wildcard differs from most typical applications 
                                                                             where IP addresses are masked. Rather than restricting the defined IP 
                                                                             address to a range of addresses by masking off the lowest significant
                                                                             bits of the address, the IP address mask is used as a wildcard.

                                                                             Each bit in the dest-wildcard-mask set to zero indicates that the 
                                                                             corresponding bit position in the packet's source IP address must exactly
                                                                             match the bit value in the corresponding bit position in the dest-wildcard-mask.
                                                                             Each wildcard bit set to one indicates that both a zero bit and a one bit
                                                                             in the corresponding position of the packet's IP address will be considered a
                                                                             match to this access list entry. In other words, 'ones' are places in bit 
                                                                             positions that should be ignored. The set of 'ones' does not have to start at 
                                                                             LSB, nor has to cover consecutive bit positions. For example, a value of 
                                                                             0.0.255.1 is valid for an IPv4 wildcard.";
				                            }
			                            }
			                            list source-ipv4-addr-filter {
			                                max-elements 1;
			                                key source-addr;
				                            leaf source-addr {
				                                mandatory true;
				                                type inet:ipv4-address;
				                            }
				                            leaf source-wildcard-mask {
				                                mandatory true;
				                                type inet:ipv4-address;
                                                                description "The source-wildcard-mask attribute defines which bits of the packet's 
                                                                             source IP address are matched to the source-wildcard-mask attribute. The 
                                                                             usage of the IP address wildcard differs from most typical applications 
                                                                             where IP addresses are masked. Rather than restricting the defined IP 
                                                                             address to a range of addresses by masking off the lowest significant
                                                                             bits of the address, the IP address mask is used as a wildcard.

                                                                             Each bit in the source-wildcard-mask set to zero indicates that the 
                                                                             corresponding bit position in the packet's source IP address must exactly
                                                                             match the bit value in the corresponding bit position in the source-wildcard-mask.
                                                                             Each wildcard bit set to one indicates that both a zero bit and a one bit
                                                                             in the corresponding position of the packet's IP address will be considered a
                                                                             match to this access list entry. In other words, 'ones' are places in bit 
                                                                             positions that should be ignored. The set of 'ones' does not have to start at 
                                                                             LSB, nor has to cover consecutive bit positions. For example, a value of 
                                                                             0.0.255.1 is valid for an IPv4 wildcard.";
				                            }
			                            }
			                            uses acl-filter-group;
			                            container yang-ext {
			                                ccap:extensionPoint; //different pyang flags impact use of this hint
			                                description "node for vendor YANG extensions";
			                            }
		                            }
		                        }
		                        case ipv6
		                        {
		                            container ipv6-rule
		                            {
			                            description "This rule matches all of the defined elements.
			                                         If no filters are defined, it matches all IPv6 packets.";
			                            list dest-ipv6-addr-filter {
			                                max-elements 1;
			                                key dest-addr;
				                            leaf dest-addr {
				                                mandatory true;
				                                type inet:ipv6-address;
				                            }
				                            leaf dest-wildcard-mask {
				                                mandatory true;
				                                type inet:ipv6-address;
                                                                description "The dest-wildcard-mask attribute defines which bits of the packet's 
                                                                             source IP address are matched to the dest-wildcard-mask attribute. The 
                                                                             usage of the IP address wildcard differs from most typical applications 
                                                                             where IP addresses are masked. Rather than restricting the defined IP 
                                                                             address to a range of addresses by masking off the lowest significant
                                                                             bits of the address, the IP address mask is used as a wildcard.

                                                                             Each bit in the dest-wildcard-mask set to zero indicates that the 
                                                                             corresponding bit position in the packet's source IP address must exactly
                                                                             match the bit value in the corresponding bit position in the dest-wildcard-mask.
                                                                             Each wildcard bit set to one indicates that both a zero bit and a one bit
                                                                             in the corresponding position of the packet's IP address will be considered a
                                                                             match to this access list entry. In other words, 'ones' are places in bit 
                                                                             positions that should be ignored. The set of 'ones' does not have to start at 
                                                                             LSB, nor has to cover consecutive bit positions. For example, a value of 
                                                                             0.0.255.1 is valid for an IPv4 wildcard.";
				                            }
			                            }
			                            list source-ipv6-addr-filter {
			                                max-elements 1;
			                                key source-addr;
				                            leaf source-addr {
				                                mandatory true;
				                                type inet:ipv6-address;
				                            }
				                            leaf source-wildcard-mask {
				                                mandatory true;
				                                type inet:ipv6-address;
                                                                description "The source-wildcard-mask attribute defines which bits of the packet's 
                                                                             source IP address are matched to the source-wildcard-mask attribute. The 
                                                                             usage of the IP address wildcard differs from most typical applications 
                                                                             where IP addresses are masked. Rather than restricting the defined IP 
                                                                             address to a range of addresses by masking off the lowest significant
                                                                             bits of the address, the IP address mask is used as a wildcard.

                                                                             Each bit in the source-wildcard-mask set to zero indicates that the 
                                                                             corresponding bit position in the packet's source IP address must exactly
                                                                             match the bit value in the corresponding bit position in the source-wildcard-mask.
                                                                             Each wildcard bit set to one indicates that both a zero bit and a one bit
                                                                             in the corresponding position of the packet's IP address will be considered a
                                                                             match to this access list entry. In other words, 'ones' are places in bit 
                                                                             positions that should be ignored. The set of 'ones' does not have to start at 
                                                                             LSB, nor has to cover consecutive bit positions. For example, a value of 
                                                                             0.0.255.1 is valid for an IPv4 wildcard.";
				                            }
			                            }
			                            uses acl-filter-group;
			                            container yang-ext {
			                                ccap:extensionPoint; //different pyang flags impact use of this hint
			                                description "node for vendor YANG extensions";
			                            }
		                            }
		                        }
		                        case yang-choice-ext {
		                            ccap:extensionPoint; //different pyang flags impact use of this hint
		                            description "node for vendor YANG extensions";
		                        }
		                    }
                            container yang-ext2 {
                                ccap:extensionPoint; //different pyang flags impact use of this hint
                                description "node for vendor YANG extensions";
                            }
                        }
                        case yang-choice-ext {
                            ccap:extensionPoint; //different pyang flags impact use of this hint
                            description "node for vendor YANG extensions";
                        }
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
        container interface {
            description "The interface object is the primary container of Interface configuration objects.";
            list cable-bundle {
                key interface-index;
                min-elements 0;
                description "A CableBundle is a compact way of assigning Layer 3 network addresses to a set of Layer 2 interfaces.  This allows the bundled Layer 2 interfaces to share a common pool of IPv4 Subnets or IPv6 prefixes so that these IP address resources can be efficiently used by the CCAP.";
                uses virtual-interface-group;
                leaf dhcp-giaddr-primary {
                    type inet:ipv4-address;
                    description "This attribute configures how the DHCP relay agent populates the GiAddr for relayed DHCP traffic. Is optional for IPv6-only bundles and required for bundles using IPv4.";
                }
                list secondary-giaddr {
                    key dhcp-giaddr-secondary;
                    description "The secondary GIADDR addresses";
                    leaf dhcp-giaddr-secondary {
                        type inet:ipv4-address;
                    }
                    leaf application {
                        type application-type;
                        default all;
                    }
	                container yang-ext {
	                    ccap:extensionPoint; //different pyang flags impact use of this hint
	                    description "node for vendor YANG extensions";
	                }
                }
                choice mac-domain {
                    case docs-md {
                        list docsis-mac-domain {
                            key docsis-mac-domain-name;
                            leaf docsis-mac-domain-name {
                                type leafref {
                                    path "/ccap/docsis/docs-mac-domain/mac-domain/mac-domain-name";
                                }
                                description "Reference to a specific docsis mac-domain-configuration list entry";
                            }
                            container yang-ext {
                                ccap:extensionPoint; //different pyang flags impact use of this hint
                                description "node for vendor YANG extensions";
                            }
                        }
                    }
                    case epon-md {
                        list epon-mac-domain {
                            key epon-mac-domain-name;
                            leaf epon-mac-domain-name {
                                type leafref {
                                    path "/ccap/epon/epon-mac-domain-config/mac-domain-name";
                                }
                                description "Reference to a specific epon mac-domain-configuration list entry";
                            }
                            container yang-ext {
                                ccap:extensionPoint; //different pyang flags impact use of this hint
                                description "node for vendor YANG extensions";
                            }
                        }
                    }
                    case yang-choice-ext {
                        ccap:extensionPoint; //different pyang flags impact use of this hint
                        description "node for vendor YANG extensions";
                    }
                }
                list cable-helper-config {
                    key cable-helper-config-index;
                    min-elements 0;
                    description "The cable-helper-config configuration object allows the operator to configure different CableHelper addresses for DHCP Clients.  These CableHelper addresses are tied to the CableBundle interfaces and the MAC Domains they service.";
                    leaf cable-helper-config-index {
                        type uint32;
                        mandatory true;
                        description "The index for the CableHelperCfg instance.";
                    }
                    container cable-helper-address {
                        uses host;
                        description "This attribute configures the IP address/hostname of the DHCP server configured as a cable helper.";
                    }
                    leaf application {
                        type application-type;
                        default all;
                        description "This attribute configures the device class for which this cable helper configuration applies.";
                    }
                    container yang-ext {
                        ccap:extensionPoint; //different pyang flags impact use of this hint
                        description "node for vendor YANG extensions";
                    }
                }
                leaf ingress-acl {
                    type leafref {
                        path "/ccap/network/acl/acl-name";
                    }
                }
                leaf egress-acl {
                    type leafref {
                        path "/ccap/network/acl/acl-name";
                    }
                }
                container yang-ext {
                    ccap:extensionPoint; //different pyang flags impact use of this hint
                    description "node for vendor YANG extensions";
                }
            }
            list loopback {
                key interface-index;
                min-elements 0;
                description "A loopback interface is a logical interface that is not tied to a specific hardware port.  It provides a virtual interface to assist in overall system configuration.  ";
                uses virtual-interface-group;
                container yang-ext {
                    ccap:extensionPoint; //different pyang flags impact use of this hint
                    description "node for vendor YANG extensions";
                }
            }
            container mgmd-router-interface {
                description "This configuration object allows for configuration of the CCAP IP Multicast Router.";
                reference "RFC 5519 Multicast Group Membership Discovery MIB";
                leaf query-interval {
                    type uint32;
                    units seconds;
                    default 125;
                    description "The frequency in seconds at which IGMP or MLD Host-Query packets are transmitted on this interface.";
                }
                leaf version {
                    type igmp-version-type;
                    default igmp-v2-or-mld-v1;
                    description "The version of MGMD that is running on this interface. This object can be used to configure a router capable of running either version. For IGMP and MLD to function correctly, all routers on a LAN must be configured to run the same version on that LAN";
                }
                leaf query-max-response-time {
                    type uint32 {
                        range "0..31744";
                    }
                    units "tenths of seconds";
                    default 100;
                    description "The maximum query response interval in seconds advertised in MGMDv2 or IGMPv3 queries on this interface.";
                }
                leaf robustness {
                    type uint32 {
                        range "1..225";
                    }
                    default 2;
                    description "The robustness variable utilized by an MGMDv3 host in sending state-change reports for multicast routers. To ensure the state-change report is not missed, the host retransmits the state-change report [mgmdHostInterfaceVersion3Robustness - 1] times. The variable must be a non-zero value.";
                }
                leaf last-member-query-interval {
                    type uint32 {
                        range "0..31744";
                    }
                    units "tenths of seconds";
                    default 10;
                    description "The Last Member Query Interval is the Max Query Response Interval in tenths of a second inserted into group-specific queries sent in response to leave group messages, and is also the amount of time between group-specific query messages. This value may be tuned to modify the leave latency of the network. A reduced value results in reduced time to detect the loss of the last member of a group. The value of this object is irrelevant if mgmdRouterInterfaceVersion is 1.";
                }
                container yang-ext {
                    ccap:extensionPoint; //different pyang flags impact use of this hint
                    description "node for vendor YANG extensions";
                }
            }
            container yang-ext {
                ccap:extensionPoint; //different pyang flags impact use of this hint
                description "node for vendor YANG extensions";
            }
        }
        container management {
            description "The management object is the primary container of Management configuration objects.";
            container ipdr {
                description "The ipdr object is the container for the IPDR configuration objects.";
                container exporter-config {
                    description "Exporter-config allows an IPDR Exporter to be turned on and off.";
                    leaf enabled {
                        type boolean;
                        default true;
                        description "This attribute configures whether or not the IPDR Exporter is enabled.";
                    }
                    leaf ipdr-exporter-listener-interface-name {
                        type string;
                        description "Local IP interface; must be a configured ip-interface name. This specifies the IP interface on which the IPDR server listens. If an IP interface is not specified, the behavior of the CCAP is vendor specific.";
                    }
                    container yang-ext {
                        ccap:extensionPoint; //different pyang flags impact use of this hint
                        description "node for vendor YANG extensions";
                    }
                }
                list streaming-session {
                    key session-id;
                    min-elements 0;
                    description "This configuration object is used to configure global IPDR connection attributes. A typical use case is for a single Template to be associated with a StreamingSession.";
                    leaf session-id {
                        type uint16;
                        mandatory true;
                        description "This attribute configures the ID for this instance.";
                    }
                    leaf keep-alive-interval {
                        type uint16;
                        units seconds;
                        default 20;
                        description "This attribute configures the interval in seconds at which IPDR 'keepalives' are sent from the CCAP IPDR exporter to the collector.";
                    }
                    leaf ack-time-interval {
                        type uint8 {
                            range "1..60";
                        }
                        units seconds;
                        default 30;
                        description "This attribute configures the interval in seconds in which the CCAP IPDR exporter waits for an acknowledgment.";
                    }
                    leaf ack-sequence-interval {
                        type uint16 {
                            range "1..500";
                        }
                        units records;
                        default 200;
                        description "This attribute configures the maximum number of unacknowledged records that can be sent by the CCAP IPDR exporter before receiving an acknowledgement.";
                    }
                    leaf collection-interval {
                        type uint32 {
                            range "0..86400";
                        }
                        units seconds;
                        mandatory true;
                        description 
                            "Where streaming is of the type timeInterval, this attribute configures the interval in seconds at which IPDR information is extracted from the CCAP management objects and transmitted to the collector. 
                             Where streaming is of the type timeEvent, this attribute identifies the interval at which the CCAP IPDR exporter will close the IPDR session to allow IPDR session processing to occur. Records created by Service Definitions supporting timeEvent are sent when the event is generated.";
                    }
                    leaf streaming-type {
                        type ipdr-streaming-type;
                        mandatory true;
                        description "This attribute configures the type of IPDR streaming used for the session.";
                    }
                    leaf enabled {
                        type boolean;
                        default true;
                        description "This attribute controls whether the IPDR Session is enabled or disabled.";
                    }
                    list service-definition-template {
                        key service-definition-id;
                        min-elements 1;
                        leaf service-definition-id {
                            type ipdr-service-definition-type;
                            description "This list configures the service type definition(s) for this IPDR session. See the IPDR Service Definition Schemas section of [OSSIv3.0] for the definitions and schemas of the types defined in this enumeration. The value of other(1) is used when a vendor-extension has been implemented for this attribute.";
                        }
                        container yang-ext {
                            ccap:extensionPoint; //different pyang flags impact use of this hint
                            description "node for vendor YANG extensions";
                        }
                    }
                    list collector-reference {
                        key collector-id;
                        leaf collector-id {
                            type leafref {
                                path "../../../collector/collector-id";
                            }
                            description "A reference to a collector id.";
                        }
                        container yang-ext {
                            ccap:extensionPoint; //different pyang flags impact use of this hint
                            description "node for vendor YANG extensions";
                        }
                    }
                    container yang-ext {
                        ccap:extensionPoint; //different pyang flags impact use of this hint
                        description "node for vendor YANG extensions";
                    }
                }
                list collector {
                    key collector-id;
                    min-elements 0;
                    description "This configuration object allows the operator to configure an IPDR collector.";
                    leaf collector-id {
                        type uint8;
                        mandatory true;
                        description "This key configures a unique identifier for this collector instance.";
                    }
                    leaf collector-ip {
                        type inet:ip-address;
                        mandatory true;
                        description "This attribute configures the IP address of collectors from which the CCAP will accept a connect. As per [OSSIv3.0], the collector establishes a connection to the CCAP";
                    }
                    leaf collector-name {
                        type string;
                        default "";
                        description "This attribute configures a name for the IPDR collector. ";
                    }
                    leaf collector-port {
                        type inet:port-number;
                        default 4737;
                        description "This attribute configures the port used by the collector to communicate with the CCAP.";
                    }
                    leaf priority {
                        type uint8;
                        mandatory true;
                        description "This attribute configures the priority of this IPDR collector. The priority is used to elect the primary and active collector. The collector with the lowest priority is elected.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container fault-management {
                description "The fault-management object is the primary container of fault management configuration objects. ";
                container event-throttle-config {
                    description "This configuration object is based on the docsDevEvent object defined in [RFC 4639] and will be used without modification for CCAP.
";
                    reference "RFC 4639 docsDevEvent Group";
                    leaf throttle-admin-state {
                        type event-throttle-admin-state-type;
                        default unconstrained;
                        description "Refer to RFC 4639.";
                    }
                    leaf threshold {
                        type uint32;
                        units events;
                        default 0;
                        description "Refer to RFC 4639.";
                        reference "RFC 4639";
                    }
                    leaf interval {
                        type uint32 {
                            range "1..2147483647";
                        }
                        units seconds;
                        default 1;
                        description "Refer to RFC 4639.";
                        reference "RFC 4639";
                    }
                    container yang-ext {
                        ccap:extensionPoint; //different pyang flags impact use of this hint
                        description "node for vendor YANG extensions";
                    }
                }
                list event-reporting-config {
                    key priority;
                    min-elements 0;
                    description "This configuration object is based on the docsDevEvControlTable object defined in [RFC 4639] and will be used without modification for CCAP.

";
                    reference "RFC 4639 docsDevEvControlTable";
                    leaf priority {
                        type syslog-priority-type;
                        mandatory true;
                        description "See RFC 4639 -- docsDevEvPriority";
                    }
                    leaf reporting {
                        type syslog-reporting-type;
                        mandatory true;
                        description "See RFC 4639 -- docsDevEvReporting";
                    }
                    container yang-ext {
                        ccap:extensionPoint; //different pyang flags impact use of this hint
                        description "node for vendor YANG extensions";
                    }
                }
                list cmts-event-ctrl {
                    key event-id;
                    min-elements 0;
                    description 
                        "This configuration object is defined in [OSSIv3.0] and will be used with no modifications for CCAP.
                         This object represents the control mechanism to enable the dispatching of events based on the Event Id. The following rules define the event control behavior:
                         - If the CmtsEventCtrl object has no instances or contains an instance with Event ID 0, then all events matching the Local Log settings of docsDevEvReporting are sent to local log ONLY.
                         - Additionally, if The CmtsEventCtrl object contains configured instances, then Events matching the Event Ids configured in the object are sent according to the settings of the docsDevEvReporting object; i.e., Traps, Syslog, etc. ";
                    reference 
                        "DOCSIS 3.0 Operations Support System Interface Specification
                         CM-SP-OSSIv3.0-I15-110623 CmtsEventCtrl Object section.";
                    leaf event-id {
                        type uint32;
                        description "This attribute represents the Event ID of the event being enabled to delivery to a dispatch mechanism (e.g. syslog).";
                    }
                    container yang-ext {
                        ccap:extensionPoint; //different pyang flags impact use of this hint
                        description "node for vendor YANG extensions";
                    }
                }
                choice snmp-trap-enable {
	                case trap-enable {
	                    description "This configuration object contains attributes which allow enabling or disabling of SNMP Notifications. The SnmpEnableAuthenTraps [RFC 3418] attribute will be used without modification for the CCAP.
	
	
	";
	                    reference "RFC 3418 snmpEnableAuthenTraps";
	                    leaf snmp-enable-authen-traps {
	                        type boolean;
	                        mandatory true;
	                        description "See RFC 3418";
	                        reference "RFC 3418";
	                    }
	                    container trap-enable-yang-ext {
	                        ccap:extensionPoint; //different pyang flags impact use of this hint
	                        description "node for vendor YANG extensions";
	                    }
	                }
                }
                list interface-trap-enable {
                    key if-name;
                    min-elements 0;
                    description 
                        "This configuration object is based on the ifLinkUpDownTrapEnable object defined in [RFC 2863] and will be used without modifications for CCAP.
                         The LinkUpDownTrapEnable attribute is configurable per ifIndex from the ifTable, as described in [OSSIv3.0].";
                    reference "[RFC 2863] ifLinkUpDownTrapEnable
";
                    leaf if-name {
                        type string {
                            length "0..255";
                        }
                        description "The path name of the interface.";
                        reference "RFC 2863 ifName";
                    }
                    leaf link-up-down-trap-enable {
                        type boolean;
                        mandatory true;
                        description "See RFC 2863";
                        reference "RFC 2863 ifLinkUpDownTrapEnable";
                    }
                    container yang-ext {
                        ccap:extensionPoint; //different pyang flags impact use of this hint
                        description "node for vendor YANG extensions";
                    }
                }
                list syslog-server-config {
                    key syslog-server-config-index;
                    min-elements 0;
                    description "This object allows the configuration of a specific Syslog Server.";
                    leaf syslog-server-config-index {
                        type uint32;
                        description "This key represents the unique identifier of an instance in this object.";
                    }
                    container syslog-server {
                        uses host;
                        description "This attribute represents the IP address/hostname of the syslog server.";
                    }
                    leaf enabled {
                        type boolean;
                        default false;
                        description "Indicates if the syslog server is used for sending syslog messages or is disabled.";
                    }
                    leaf syslog-source-ip-interface-name {
                        type string;
                        description "Local IP interface; must be a configured ip-interface name. If not specified, then the vendor picks the source IP address";
                    }
                    container yang-ext {
                        ccap:extensionPoint; //different pyang flags impact use of this hint
                        description "node for vendor YANG extensions";
                    }
                }
                container diag-log-triggers-config {
                    description 
                        "This configuration object is based on the LogTriggersCfg object in Annex G of [OSSIv3.0] and will be used without modification for CCAP.
                         This object defines the parameters to configure the Diagnostic Log triggers. One or more triggers can be configured to define the actions of creating or updating CM entries into the Diagnostic Log.";
                    reference 
                        "DOCSIS 3.0 Operations Support System Interface Specification
                         CM-SP-OSSIv3.0-I15-110623 LogTriggersCfg Object section.";
                    leaf include-triggers {
                        type trigger-flag-type;
                        default registration;
                        description "This attribute turns individual diagnostic triggers on and off at a given time when each trigger is set to '1' or '0' respectively.";
                    }
                    leaf enable-aging-triggers {
                        type trigger-flag-type;
                        default " ";
                        description "This attribute enables and disables the aging of individual triggers at a given time when each trigger is set to '1' or '0 respectively.  If a log entry is added by multiple triggers, and aging is disabled for one of those triggers, the CMTS MUST NOT age out such entry.";
                    }
                    leaf reg-time-interval {
                        type uint32 {
                            range "60..86400";
                        }
                        units seconds;
                        default 90;
                        description "This attribute is an operator empirically derived, worst-case number of seconds which the CM requires to complete registration. If the CM has not completed the registration stage within this registration time interval, the CM will be added to the Diagnostic Log.";
                    }
                    leaf reg-detail {
                        type reg-detail-type;
                        default " ";
                        description "Setting a bit representing a CM registration state will enable counting the number of times the CMTS determines that such CM reaches that state as the last state before failing to proceed further in the registration process and within the time interval considered for the CM registration trigger detection.";
                    }
                    leaf ranging-retry-trigger {
                        type ranging-retry-trigger-type;
                        default consecutive-miss;
                        description "This attribute selects the type of ranging retry trigger to be enable in the Diagnostic Log.";
                    }
                    leaf ranging-retry-threshold {
                        type uint8 {
                            range "3..12";
                        }
                        default 6;
                        description "This attribute indicates the number of times the CMTS does not detect a CM acknowledgement of a MAC-layer station maintenance message from a CMTS to be exceeded in order to add the CM to the Diagnostic Log. The value of RangingRetryType decides if consecutive ranging miss or ranging miss ratio is used as trigger.";
                    }
                    leaf ranging-retry-station-maint-num {
                        type uint16 {
                            range "60..65535";
                        }
                        default 90;
                        description "This attribute indicates the number of station maintenance opportunities to monitor for ranging retry trigger. This value implies time intervals in a certain range. DOCSIS specifies that the CMTS schedules ranging opportunities to CMs sufficiently smaller than T4. There is no fixed formula to derive at a fixed time interval, how many ranging opportunities may be offered to a CM by the CMTS, hence using the number of station maintenance opportunities provides ratio with the fixed denominators while also taking time factor into consideration.";
                    }
                    container yang-ext {
                        ccap:extensionPoint; //different pyang flags impact use of this hint
                        description "node for vendor YANG extensions";
                    }
                }
                container diag-log-global-config {
                    description "This object defines the parameters to manage and control the instantiation of CMs in the Diagnostic Log object.";
                    leaf max-size {
                        type uint32 {
                            range "1..4294967295";
                        }
                        units instances;
                        default 100;
                        description "This attribute indicates the maximum number of CM instances that can be reported in the DiagLog.";
                    }
                    leaf notify-log-size-high-thrshld {
                        type uint32 {
                            range "1..4294967295";
                        }
                        units instances;
                        default 80;
                        description "This attribute is the high threshold value to send a  HighThreshold notification when the number of instances in the DiagLog exceeds this value.";
                    }
                    leaf notify-log-size-low-thrshld {
                        type uint32 {
                            range "1..4294967295";
                        }
                        units instances;
                        default 60;
                        description "This attribute is the threshold value to send a  LowThreshold notification when the number of instances in DiagLog drops to this value, but only if the DiagLog number of instances exceeded the NotifyLogSizeHighThrshld value.";
                    }
                    leaf aging {
                        type uint32 {
                            range "15..86400";
                        }
                        units minutes;
                        default 10080;
                        description "This attribute defines a period of time after which an instance in the DiagLog and its corresponding  DiagLogDetail  instance (if present)  are removed if no longer the DiagLog instance is updated due to a trigger detection process.";
                    }
                    leaf notif-ctrl {
                        type notif-ctrl-type;
                        default " ";
                        description "This attribute is used to enable diagnostic log related notifications.";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container snmp {
                description "This object defines the configuration of access control for SNMPv1/v2c received request messages. When a SNMP request message is received, the system checks the validity of the request by matching the community string, source (IP address, subnet),  access type and view restrictions  for included SNMP OIDs in the request.";
                list access-config {
                    key community;
                    min-elements 0;
                    description "This object defines the configuration of access control for SNMPv1/v2c received request messages. When a SNMP request message is received, the system checks the validity of the request by matching the community string, source (IP address, subnet),  access type and view restrictions  for included SNMP OIDs in the request.";
                    leaf community {
                        type string {
                            length "1..32";
                        }
                        mandatory true;
                        description "The community string defined for the access control rule.";
                    }
                    leaf ip-address {
                        type inet:ip-prefix;
                        mandatory true;
                        description "The prefix used to validate the source of an incoming SNMP request.";
                    }
                    leaf type {
                        type snmp-access-type;
                        default read-only;
                        description "Defines the type of access granted to the SNMP request.";
                    }
                    uses view-config-ref;
                    container yang-ext {
                        ccap:extensionPoint; //different pyang flags impact use of this hint
                        description "node for vendor YANG extensions";
                    }
                }
                list view-config {
                    key view-name;
                    min-elements 0;
                    description "This object defines a View consisting of a single OID subtree matching rule for inclusion or exclusion as part of a SNMP message processing procedure such as access authorization or dispatch or notifications";
                    leaf view-name {
                        type string {
                            length "1..32";
                        }
                        mandatory true;
                        description "The administrative name of an instance of this object.";
                    }
                    leaf subtree {
                        type string;
                        mandatory true;
                        description 
                            "The OID subtree to be matched for the access view. This attribute is formatted as the text representation of an ASN.1 OID following the ABNF notation below:
                             Subtree =  empty | OID [.OID]*
                             OID = number ; 0..128
                             The matching procedures are borrowed from [RFC 3414] for tree views matching with the difference that the configuration elements uses a text notation to represent OIDs and OID masks. See the subtree-mask attribute definition for further information.";
                    }
                    leaf subtree-mask {
                        type string;
                        mandatory true;
                        description 
                            "A mask to match OIDs for inclusion or exclusion as part of the view. This attribute definition is borrowed from [RFC 3414]. The only difference is that instead of bits per OID, a byte of value '0' or '1' is used to represent this attribute. 
                             Each byte value 1 indicates the inclusion of the corresponding OID position in the Subtree attribute, while the value 0 indicates no need to match. See [RFC 3414] for details.";
                    }
                    leaf type {
                        type subtree-view-inclusion-type;
                        mandatory true;
                        description "Indicates inclusion or exclusion of the subtree for the defined view.";
                    }
                    container yang-ext {
                        ccap:extensionPoint; //different pyang flags impact use of this hint
                        description "node for vendor YANG extensions";
                    }
                }
                list notification-receiver-config {
                    key notification-receiver-name;
                    min-elements 0;
                    description "This object defines where to send notifications. When an event is to be dispatched as a notification, the system checks for instances of this object that have the notification OID associated with the event as part of their Inclusion list in their view-configuration instances. The system then sends notifications based on the matched occurrences per their configured parameters.";
                    leaf notification-receiver-name {
                        type string {
                            length "1..32";
                        }
                        mandatory true;
                        description "The administrative name of an instance in this object.";
                    }
                    leaf type {
                        type notification-type;
                        default snmpv2c-trap;
                        description "Indicates the type of SNMP notification being sent.";
                    }
                    container notification-receiver {
                        uses host;
                        description "The IP address/hostname of the notification receiver.";
                    }
                    leaf notification-receiver-port {
                        type inet:port-number;
                        default 162;
                        description "The UDP port that the notification receiver listens on for messages.";
                    }
                    leaf timeout {
                        type uint8;
                        units seconds;
                        default 1;
                        description "The time in seconds the sender waits for receiving confirmation for a notification being sent. This attribute is meaningful only when the attribute type is set to 'snmpv2c-inform'; otherwise it is ignored.";
                    }
                    leaf retries {
                        type uint8;
                        default 3;
                        description "The number of retries the sender will attempt in case of it has not received confirmation of inform reception. This attribute is meaningful only when the attribute type is set to 'snmpv2c-inform'; otherwise it is ignored.";
                    }
                    uses view-config-ref;
                    leaf notif-source-ip-interface-name {
                        type string;
                        description "Local IP interface; must be a configured ip-interface name. If not specified, then the vendor picks the source IP address";
                    }
                    container yang-ext {
                        ccap:extensionPoint; //different pyang flags impact use of this hint
                        description "node for vendor YANG extensions";
                    }
                }
                container yang-ext {
                    ccap:extensionPoint; //different pyang flags impact use of this hint
                    description "node for vendor YANG extensions";
                }
            }
            container yang-ext {
                ccap:extensionPoint; //different pyang flags impact use of this hint
                description "node for vendor YANG extensions";
            }
        }
        container yang-ext {
            ccap:extensionPoint; //different pyang flags impact use of this hint
            description "node for vendor YANG extensions";
        }
    }
    container ccap {
        description "The CCAP object serves as the root of the CCAP configuration data.  It consists of three attributes that together describe the CCAP platform. ";
    	uses ccap-group;
    }
}
