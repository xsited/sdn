module orchestration
{
	namespace "http://cablelabs.com/yang/nfv/orchestration";
	prefix cablelabs;


  	import ietf-yang-types {
    		prefix yang;
    		revision-date 2010-09-24;
  	}
  	import ietf-inet-types {
    		prefix inet;
    		revision-date 2010-09-24;
  	}




  	organization "CableLabs, Inc.";
  	contact "Thomas Kee <t.kee@cablelabs.com>";

	description
	"This module contains data types and rpc definitions for the nfv orchestration layer;"


  	revision 2014-07-04 {
    		description
      		"Initial revision";
    		reference 
		"";
  	}

	typedef up-down-state-type {
		type enumeration {
			enum up;
			enum down;
		}
		description
		"Type for specifying state of a circuit.";
	}


	typedef tenant-reference {
		type string;
		description
		"Type to identify the tenant or project";
	}

	typedef vnf-reference {
		type string;
		description
		"Type to identify the VNF";
	}


	grouping vnf-grouping
	{
		description
		"Reserve VIM resources for VNF";

		leaf enabled {
			type boolean;
			default false;
			description
			"Specifies if the VNF is enabled.";
		}

		leaf vnf-id {
			type vnf-id;
			mandatory true;
			description
			"The ID of the VNF.";
		}
		leaf vnf-state
		{
			type up-down-state-type;
			default down;
			description
			"The VNF up or down";

		}

/* XXX - Need a reference to the resources managed by VNFM
		container vims-managed
		{
			list vims-managed {
				key "vm-id";
				unique "vm-id";
				description
				"The list of all VM instances used by the VNF.";
				uses vim-attributes-grouping;
			}
		}
*/

	}

	rpc orchestration_nfv_create {
			description
			"Create a VNF";
			reference "";

			input {
				leaf tenant-id
				{
					type tenant-reference;
				}

				container vnf-input
				{
					uses vnf-grouping; //attributes
				}

			}
			output {
				leaf status
				{
					type uint32;
				}
				leaf vnf-id
				{
					type vnf-id;
				}
			}
	}

			// XXX create VNF
	rpc orchestration_nfv_get {
			description
			"Get a VNF ";

			reference "";

			input {
				leaf tenant-id
				{
					type tenant-reference;
				}

				leaf vnf-id
				{
				     type vnf-id;
				}

			}
			output {
				leaf status
				{
				     type uint32;
				}
				container vnf-output
				{
				     uses vnf-grouping; //attributes
				}

			}
	}


		// XXX create VNF
	rpc orchestration_nfv_update {
			description
			"Update a VNF";

			reference "";

			input {
				leaf tenant-id
				{
					type tenant-reference;
				}

				leaf vnf-id
				{
					type vnf-id;
				}
				container vnf-input
				{
					uses vnf-grouping; //attributes
				}


			}
			output {
				leaf status
				{
					type uint32;
				}
			 }
	}

		// XXX create VNF
	rpc orchestration_nfv_delete {
			description
			"Delete a VNF ";

			reference "";

			input {
				leaf tenant-id
				{
					type tenant-reference;
				}

				leaf vnf-id
				{
					type vnf-id;
				}
				container vnf-input
				{
					uses vnf-grouping; //attributes
				}

			}
			output {
				leaf status
				{
					type uint32;
				}
			}
	}

}
