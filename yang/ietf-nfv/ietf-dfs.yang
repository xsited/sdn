/*
6. Data Model of Deployment Flavor

   A deployment flavor is a template that describes a specific
   deployment of a Virtualised Network Function supporting required
   capacity and performance.

   It refers to a set of VDUs which provide the deployment and
   operational behavior.

6.1. Deployment Flavor Module Structure

   module: ietf-dfs

      +--rw dfs

         +--rw df* [df-id]

            +--rw df-id    yang:uuid

            +--rw license-info    string

            +--rw pricing_info    string

            +--rw vdu* [vdu-id]

               +--rw vdu-id    leafref

6.2. Deployment Flavor YANG Module
*/

   module ietf-dfs {

       namespace "urn:ietf:params:xml:ns:yang:ietf-dfs";

       prefix "df";

       import ietf-yang-types {

         prefix yang;

       }

       import ietf-vdus {

         prefix vdu;

       }

        organization "";

        contact "TBD";

       description

        "This module defines a deployment flavor descriptor.

         Copyright (c) 2014 IETF Trust and the persons

         identified as authors of the code.  All rights reserved.

         Redistribution and use in source and binary forms, with or

         without modification, is permitted pursuant to, and subject

         to the license terms contained in, the Simplified BSD License

         set forth in Section 4.c of the IETF Trust's Legal Provisions

         Relating to IETF Documents


         (http://trustee.ietf.org/license-info).

         This version of this YANG module is part of RFC XXXX; see

         the RFC itself for full legal notices.";

       revision "2014-05-18" {

         description

           "Initial version";

         reference "RFC XXXX";

       }

       container dfs {

         description

           "Deployment Flavors";

         list df {

           key df-id;

           description

             "Deployment flavor key";

           leaf df-id {

             type yang:uuid;

             description

               "Deployment flavor ID";

           }

           leaf license-info {

             type string;

             description

               "Software licenses required for supporting this deployment flavour.";

           }

           leaf pricing_info {

             type string;

             description

               "Pricing information required for supporting this deployment flavour.";

           }

           list vdu {

             key vdu-id;

             description

               "Refer to a VDU used for this deployment flavor";

             leaf vdu-id {

               type leafref {

                 path "/vdu:vdus/vdu:vdu/vdu:id";

               }


               description

                 "Vdu ID";

             }

           }

         }

       }

   }
