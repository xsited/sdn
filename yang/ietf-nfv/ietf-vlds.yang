/*
7. Data Model of Virtual Link Descriptor (VLD)

   VLD describes the resource requirements that are needed for a
   virtualization link.

7.1. VLD Module Structure

   module: ietf-vlds

      +--rw vlds

         +--rw vld* [id]

            +--rw id                    yang:uuid

            +--rw vendor?               string

            +--rw version?              string

            +--rw number_of_enpoints?   uint32

            +--rw virtual-link-type?    enumeration

7.2. VLD YANG Module
*/

   module ietf-vlds {

       namespace "urn:ietf:params:xml:ns:yang:ietf-vlds";

       prefix "vld";

       import ietf-yang-types {

         prefix yang;

       }

        organization "";

        contact "TBD";

       description

        "This module defines a virtual link descritor.

         Copyright (c) 2014 IETF Trust and the persons

         identified as authors of the code.  All rights reserved.

         Redistribution and use in source and binary forms, with or

         without modification, is permitted pursuant to, and subject

         to the license terms contained in, the Simplified BSD License

         set forth in Section 4.c of the IETF Trust's Legal Provisions

         Relating to IETF Documents

         (http://trustee.ietf.org/license-info).

         This version of this YANG module is part of RFC XXXX; see

         the RFC itself for full legal notices.";

       revision "2014-05-18" {

         description

           "Initial version";

         reference "RFC XXXX";

       }

       container vlds {

         description

           "Virtual Link Descriptors";

         list vld {

           key id;

           description

             "VLD Key";

           leaf id {

             type yang:uuid;

             description

               "VLD ID";

           }

           leaf vendor {

             type string;

             description

               "Vendor generating this VLD";

           }

           leaf version {

             type string;

             description

               "Version of this VLD";

           }

           leaf number-of-endpoints {

             type uint32;

             description

               "Number of endpoints available on this VLD";

           }

           leaf virtual-link-type {

             type enumeration {

               enum "ELine";

               enum "ELAN";

               enum "ETree";

             }

             description

               "Virtual network link type mandated by the VNF vendor between two or more connection points";

           }

         }

       }

   }
