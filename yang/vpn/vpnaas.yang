module vpnaas
{
      namespace "http://cablelabs.com/yang/vpnaas/";
        prefix vpnaas;


    import ietf-yang-types 	{ prefix yang; }
    import ietf-inet-types 	{ prefix inet; }
    import ietf-interfaces 	{ prefix if;   }
 

    description 
	"This module contains a collection of generic VPN definitions";
    organization 
	"CableLabs";
    contact 
	"Thomas Kee t.kee@cablelabs.com";
    revision "2014-08-09" {
        description "Initial revision of vpn";
    }        

    typedef tenant-instance {
        type instance-identifier;
    }
    typedef router-instance {
        type instance-identifier;
    }
    typedef subscriber-instance {
        type instance-identifier;
    }
    typedef circuit-instance {
        type instance-identifier;
    }
    typedef device-instance {
        type instance-identifier;
    }
    typedef service-instance {
        type instance-identifier;
    }
    typedef subnet-instance {
        type instance-identifier;
    }
  typedef vlan-id {
    type uint32 {
      range "1..4095";
    }
  }
  typedef mep-id {
    type uint32 {
      range "1..8191";
    }
  }

   grouping mep-address {
	leaf mac-address {
 	type yang:mac-address;
	}
	leaf ip-address {
	type inet:ip-address;
	}
   }

   grouping performance-statistics {
               leaf bytes {
                        type yang:counter64;
                }
                leaf packets {
                        type yang:counter64;
                }
                leaf errors {
                        type yang:counter32;
                }
                leaf dropped {
                        type yang:counter32;
                }
                leaf latency {
                        type yang:counter64;
                }

   }


    grouping router-interface {
        leaf router-id {
            type router-instance;
        }
        leaf router {
            description
            "XXX- fix me devices definitions";
            type string;
            mandatory true;
        }
        leaf interface {
            type string;
            mandatory true;
        }
    }

    leaf topology {
        type enumeration {
            enum hub-n-spoke;
            enum mesh;
            enum tree64;
        }
    }


    grouping subscriber-grouping {
        leaf subscriber-id {
            type subscriber-instance;
        }
        grouping flow-list-grouping  {
            container flows {
                list flows {
                    key "flow-id";
                    unique "flow-id";
                    description
                    "The list of all flow applied to this subscriber.";
                }
            }
        }
        grouping device-list-grouping  {
            container devices {
                list devices {
                    key "device-id";
                    unique "device-id";
                    description
                    "The list of all device applied to this subscriber.";
                }
            }
        }
        grouping circuit-list-grouping  {
            container circuits {
                list circuits {
                    key "circuit-id";
                    unique "circuit-id";
                    description
                    "The list of all circuits used for this subscriber.";
                }
            }
        }
        grouping tenant-list-grouping  {
            container tenants {
                list tenants {
                    key "tenant-id";
                    unique "tenant-id";
                    description
                    "The list of all tenant groups this subscriber belongs to";
                }
            }
        }
    }

    grouping circuit-grouping  {

        leaf protocol {
            type enumeration {
                enum l2vpn;
                enum l3vpn;
                enum ssl;
                enum ipsec;
                enum gre;
                enum vxlan;
            }
            default "l2vpn";
        }


        container endpoint-a {
            uses router-interface;
        }

        container endpoint-b {
            uses router-interface;
        }

        leaf encapsulation-type {
            type enumeration {
                enum ethernet;
                enum ethernet-vlan;
            }
        }

        leaf vlan {
            type vlan-id;
            description "VLAN, should only be defined if encapsulation type is Ethernet-VLAN";
        }

        leaf mep-id {
            type mep-id;
        }

        leaf service-id {
            type service-instance;
            description "Unique id for the service";
        }

        leaf circuit-id	{
            type circuit-instance;
            description
            "uuid-str	N/A	R	generated	N/A	UUID for VPNService Object";
            mandatory true;
        }

        leaf tenant-id	{
            type tenant-instance;
            description
            "uuid-str	Yes	CR	None	valid tenant_id	UUID of the tenant for the vpn service";
            mandatory true;
        }

        leaf subscriber-id	{
            type subscriber-instance;
            description
            "uuid-str	Yes	CR	None	valid tenant_id	UUID of the tenant for the vpn service";
            mandatory true;
        }

        leaf vpn-name	{
            description
            "string	no	CRU	None	N/A	name of the VPN Service";
            type string {
                length 64;
            }
        }

        leaf vpn-description	{
            description
            "string	no	CRU	None	N/A	Description of the VPN Service";
            type string {
                length 64;
            }
        }


        leaf vpn-status	{
            description
       "string	N/A	R	N/A	N/A	Indicates whether ipsec vpnservice is currently operational. Possible values include";
            type enumeration {
                enum "active" {
                    value 1;
                }
                enum "down" {
                    value 2;
                }
                enum "up" {
                    value 3;
                }
                enum "error" {
                    value 4;
                }
                enum "suspended" {
                    value 5;
                }
            }
        }


        leaf admin-state-up {
            description
            "bool	N/A	CRU	TRUE	true/false	Administrative state of vpnservice. If false (down), port does not forward packets";
            type boolean;
            default true;
        }

        leaf subnet-id	{
            description
            "uuid	yes*( subnet_id is needed)	CR	N/A	Valid subnet id	Subnet id in which the tenant wants the vpn service";
            type subnet-instance;
            mandatory true;
        }

        leaf router-id	{
            description
            "uuid	yes	CR	N/A	Valid router id	Router id to which the vpn service is inserted";
            type router-instance;
            mandatory true;
        }

    }


    // augment gen-oam and add mef-soam.yang
    rpc ping {
        description
        "Generate icmp and return response";
        input {
            leaf circuit_id {
                 type circuit-instance;
            }

/*
            leaf ecmp-choice {
                type ecmp-choices;
                description
                "0 means use the specified interface
                1 means use round robin";
            }
*/
            list probe-interfaces {
                key "interface";
                leaf interface {
                    //type if:interface-ref;
			type string;
                 }
             }

             container source-address {
                 uses mep-address;
                 leaf mep-id {
                     type mep-id;
                 }
             }
             container destination-address {
                 uses mep-address;
                 leaf mep-id {
                     type mep-id;
                 }
             }
         }
         output {
             uses performance-statistics;
         }
     }

     rpc iperf {
         description
         "Generate icmp and return response";

         input {
             leaf circuit-id {
                 type circuit-instance;
             }
        leaf data_length {
            type uint16;
        default 64;
        }
        leaf duration {
            type uint16;
            default 30;
        }
        container source-address {
            uses mep-address;
            leaf mep-id {
                type mep-id;
            }
        }
        container destination-address {
            uses mep-address;
            leaf mep-id {
                type mep-id;
            }
        }
        }
    output {
        uses performance-statistics ;
    }
    }


    grouping ike-policy-grouping
    {

    leaf ike-policy-id	{
        description
        "uuid-str	N/A	R	generated	N/A	UUID for  the  IKEPolicy";
        type instance-identifier;
    }

    leaf tenant-id	{
        description
        "uuid-str	Yes	CR	None	valid tenant_id	UUID for owner of the vpn service";
        type tenant-instance;
        mandatory true;
    }

    leaf ike-policy-name {
        description
        "string	yes	CRU	None	N/A	friendly name for the ikepolicy";
	type string { length 64;  }
    }

    leaf ike-policy-description {
        description
        "string	no	CRU	None	N/A	Description of the ikepolicy";
	type string;
    }

    leaf auth-algorithm {
        description
        "string	no	CRU	sha1	N/A	Authentication Hash algorithms sha1";
        type enumeration {
            enum "sha1" {
                value 1;
            }
        }
            default "sha1";
    }

    leaf encryption-algorithm {
        description
        "string	no	CRU	aes-128	N/A	Encryption Algorithms 3des, aes-128, aes-256, aes-192 etc.,";
        type enumeration {
            enum "3des" {
                value 1;
            }
            enum "aes-128" {
                value 2;
            }
            enum "aes-256" {
                value 3;
            }
            enum "aes-192" {
                value 4;
            }
        }
            default "aes-128";
    }

    leaf phase1-negotiation-mode {
        description
        "string	no	CRU	Main Mode	N/A	IKE mode Main mode";
        type enumeration {
            enum "ike" {
                value 1;
            }
            enum "main" {
                value 2;
            }
        }
            default "main";
    }

    leaf pfs {
        description
        "	string	no	CRU	Group5	N/A	Perfect Forward Secrecy  ( Group2, Group5, Group14)";
        type string;
        default "Group5";
    }

    leaf ike_version {
        description
        "string	no	CRU	v1	N/A	v1 or v2 version";
        type enumeration {
            enum "v1" {
                value 1;
            }
            enum "v2" {
                value 2;
            }
        }
        default "v1";
    }

    grouping lifetime-grouping {
        leaf units {
            description
            "string	no	CRU	seconds	seconds	Lifetime of the  SA unit in seconds";
	    type string;
	    default "seconds";
        }
        leaf value {
            description
            "	integer	no	CRU	3600 for seconds	Integer	Lifetime value in  seconds (value >= 60)";
            type uint32;
            default 3600;
        }
    }
    }


    grouping ipsec-site-connection-grouping
    {
        leaf ipsec-site-connection-id
        {
            description
            "uuid-str	N/A	R	generated	N/A	UUID for  the vpns connection";
            type instance-identifier;
        }
        leaf tenant-id
        {
            description
            "uuid-str	Yes	CR	None	valid tenant_id	UUID for owner of the  vpn service";
            type tenant-instance;
        }
        leaf ipsec-site-connection-name
        {
            description
            "string	no	CRU	None	N/A	name for ipsec-site-connection";
            type string { length 64; }
        }
        leaf ipsec-site-connection-description
        {
            description
            "string	no	CRU	None	N/A	Description of the ipsec-site-connection";
            type string;
        }
        leaf peer-address
        {
            description
            "ipaddress(v4 or v6)	yes	CRU	N/A	valid ip address (v4 or v6)	peer vpn gateway public address or FQDN";
            type inet:ip-address;
        }

        leaf peer-id
        {
            description
            "string	yes	CRU	N/A	N/A	Peer identifier ( Can be name, string or FQDN )";
            type instance-identifier;

        }
        leaf peer-cidrs
        {
            description
            "list[string]	yes	cru	n/a	list of valid cidr in the form <network_address>/<prefix>	peer private cidrs";
            type instance-identifier;
        }

        leaf route-mode
        {
            description
            "string	no	r	static	static	static";
            type string;
            default "static";
        }

        leaf mtu
        {
            description
            "integer	no	cru	1500	integer	mtu - maximum transmission unit to address fragmentation ( value>=68 )";
            type uint32 {
                range 68..1500;
            }
            default 1500;
        }

        leaf auth-mode
        {
            description
            "string	no	r	psk	psk/certs	authentication mode, either psk or certificate";
            type enumeration {
                enum "psk" {
                    value 1;
                }
                enum "certificate" {
                    value 2;
                }
            }
            default "psk";
        }
        leaf psk
        {
            description
            "string	yes	CRU	N/A	NO	Pre-shared-key any string.";
            type string;
        }

        leaf initiator
        {
            description
            "string	no	CRU	bi-directional	bi-directional / response-only	Whether this VPN can only respond to connections or can initiate as well";
            type enumeration {
                enum "bi-directional" {
                    value 1;
                }
                enum "response-only" {
                    value 2;
                }
            }
            default "bi-directional";
        }

        leaf admin-state-up
        {
            description
            "bool	N/A	CRU	TRUE	true / false	Administrative state of vpn connection. If false (down), vpn concd nection does not forward packets";
            type boolean;
            default "true";
        }


        leaf status
        {
            description
            "string	N/A	R	N/A	N/A	Indicates whether vpn connection is currently operational. Possible values include:ACTIVE,DOWN,BUILD,ERROR";
            type enumeration {
                enum "active" {
                    value 1;
                }
                enum "down" {
                    value 2;
                }
                enum "up" {
                    value 3;
                }
                enum "build" {
                    value 4;
                }
                enum "error" {
                    value 5;
                }
            }
        }

        leaf ike-policy-id
        {
            description
            "uuid	yes	CR	N/A	uuid of ikepolicy	uuid id of ikepolicy";
            type instance-identifier;
        }

        leaf ipsec-policy-id
        {
            description
            "uuid	yes	CR	N/A	uuid of ipsecpolicy	uuid id of ipsecpolicy";
            type instance-identifier;
        }

        leaf service-id
        {
            description
            "uuid	yes	CR	N/A	uuid of vpnservice	service id of vpnservice";
            type service-instance;
        }

        grouping dpd-grouping 
	{
            leaf action
            {
                description
                "string	no	CRU	hold	hold / clear / disabled /restart /restart_by_peer	DPD actions controls the use of Dead Peer Detection Protocol. ( clear, hold, restart, disabled, restart-by-peer)";
            type enumeration {
                enum "hold" {
                    value 1;
                }
                enum "clear" {
                    value 2;
                }
                enum "disabled" {
                    value 3;
                }
                enum "restart" {
                    value 4;
                }
                enum "restart_by_peer" {
                    value 5;
                }
		}
            }

            leaf interval
            {
                description
                "integer	no	CRU	30	> 0	sec for DPD delay";
		type uint32;
		default 30;
            }
            leaf timeout
            {
                description
                "integer	no	CRU	120	> 0 & > dpd_interval	sec for DPD timeout";
		type uint32;
		default 120;
            }
        }
    }
}
