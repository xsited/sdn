module vpn-tk
{
    namespace "urn:cablelabs:vpn";
    prefix "vpn";

    import ietf-yang-types 	{ prefix yang; }
    import ietf-inet-types 	{ prefix inet; }
    import ietf-interfaces 	{ prefix if;   }
    import iana-afn-safi 	{ prefix ianaaf; }


    description "This module contains a collection of generic VPN definitions";
    organization "CableLabs";
    contact "Thomas Kee t.kee@cablelabs.com";
    revision "2014-08-09" {
        description "Initial revision of vpn";
    }        
    
    typedef protocol {
	
    }

     typedef address-family {
   list vpn {
           key name;
           leaf name { type string { length 64; } }
           leaf protocol {
               type enumeration {
                   enum l2vpn;
                   enum l3vpn;
                   enum ssl;
                   enum ipsec;
               }
           }
           leaf topology {
               type enumeration {
                   enum hub-n-spoke;
                   enum mesh;
               }
           }
           list members {
               key "device interface";
               leaf device { ... }
               leaf interface { ... }
           }
           list classifiers {
           }
       }
}
