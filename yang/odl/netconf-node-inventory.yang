module netconf-node-inventory {
    namespace "urn:opendaylight:netconf-node-inventory";
    prefix "netinv";
    
    import opendaylight-inventory { prefix inv; revision-date "2013-08-19";}
/*    import yang-ext {prefix ext; revision-date "2013-07-09";} */
    
    revision "2014-01-08" {
        description "Initial revision of Inventory model";
    }
    
    grouping netconf-node-fields {
        leaf connected {
            type boolean; 
        }
    
        leaf-list initial-capability {
            type string;
        }
        
        leaf-list current-capability {
            type string;
        }
    }
    
    augment /inv:nodes/inv:node {
        ext:augment-identifier "netconf-node";
        
        uses netconf-node-fields;
    }
}
