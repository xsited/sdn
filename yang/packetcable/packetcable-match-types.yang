module packetcable-match-types
{
    namespace "urn:opendaylight:model:match:types";
    prefix "match";

    import ietf-inet-types {prefix inet; }
    import ietf-yang-types { prefix yang; }
    import packetcable-traffic-profile {prefix tp; }


    revision "2014-08-08" {
        description "Initial revision of packetcable match types";
    }        
    
    grouping "subscriber-device" {
        leaf subscriber-id {
            type inet:ip-address;
            mandatory true;
            description "An identifier that identifies a cable modem. The IP address of the CM.";
        }
        leaf mac-address {
            type yang:mac-address;
            description "The MAC address of the CM.";
        }
    }

    grouping "docsis-traffic-profiles" {
        uses tp:traffic-profile-grouping;
    }

    grouping "ip-match-fields" {
        leaf ip-protocol {
            description "IP protocol.";
            type uint8;
        }

        leaf ip-dscp {
            description "IP DSCP (6 bits in ToS field).";
            type inet:dscp;
        }

        leaf ip-ecn {
            description "IP ECN (2 bits in ToS field).";
            type uint8;
        }

        leaf ip-proto {
            description "IP Proto (IPv4 or IPv6 Protocol Number).";
	    type inet:ip-version;
        }
    }

    grouping "ipv4-match-fields" {
        leaf ipv4-source {
            description "IPv4 source address.";
            type inet:ipv4-prefix;
        }

        leaf ipv4-destination {
            description "IPv4 destination address.";
            type inet:ipv4-prefix;
        }

    }

    grouping "ipv6-match-fields" {
        leaf ipv6-source {
            description "IPv6 source address.";
            type inet:ipv6-prefix;
        }

        leaf ipv6-destination {
            description "IPv6 destination address.";
            type inet:ipv6-prefix;
        }

        leaf ipv6-nd-target {
            description "IPv6 target address for neighbour discovery message";
            type inet:ipv6-address;
        }

        container "ipv6-label" {
            leaf ipv6-flabel {
                type inet:ipv6-flow-label;
            }

            leaf flabel-mask {
                type binary;
            }
        }

        leaf ipv6-exthdr {
            description "IPv6 Extension Header field";
            type uint16;
        }
    }


    grouping "udp-match-fields" {
        leaf udp-source-port {
            description "UDP source port.";
            type inet:port-number;
        }
        leaf udp-destination-port {
            description "UDP destination port.";
            type inet:port-number;
        }
    }

    grouping "tcp-match-fields" {
        leaf tcp-source-port {
            description "TCP source port.";
            type inet:port-number;
        }
        leaf tcp-destination-port {
            description "TCP destination port.";
            type inet:port-number;
        }
    }

    grouping "udp-match-ranges" {
        leaf udp-source-port-start {
            description "UDP source port start.";
            type inet:port-number;
        }
        leaf udp-source-port-end {
            description "UDP source port end.";
            type inet:port-number;
        }
        leaf udp-destination-port-start {
            description "UDP destination port start.";
            type inet:port-number;
        }
        leaf udp-destination-port-end {
            description "UDP destination port end.";
            type inet:port-number;
        }
    }

    grouping "tcp-match-ranges" {
        leaf tcp-source-port-start {
            description "TCP source port start.";
            type inet:port-number;
        }
        leaf tcp-source-port-end {
            description "TCP source port end.";
            type inet:port-number;
        }
        leaf tcp-destination-port-begin {
            description "TCP destination port begin.";
            type inet:port-number;
        }
        leaf tcp-destination-port-end {
            description "TCP destination port end.";
            type inet:port-number;
        }
    }

    grouping match {

        container "ip-match" {
            uses "ip-match-fields";
        }

        choice layer-3-match {
        case "ipv4-match" {
                uses "ipv4-match-fields";
            }
        case "ipv6-match" {
                uses "ipv6-match-fields";
            }
        }

        description "if tpSrc then tpSrcStart = tpSrcEnd = tpSrc";
        choice layer-4-match {
        case "udp-match" {
            choice "udp-field-range" {
		    case "udp-field" {
                        uses "udp-match-fields";
		    }
		    case "udp-range" {
                        uses "udp-match-ranges";
		    }
		}
            }
        case "tcp-match" {
            choice "tcp-field-range" {
		    case "tcp-field" {
                        uses "tcp-match-fields";
		    }
		    case "tcp-range" {
                        uses "tcp-match-ranges";
		    }
		}
            }
        }
    }
}
